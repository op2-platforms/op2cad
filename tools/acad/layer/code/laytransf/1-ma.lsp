; file usage: major commands and string data for laytranf function
;
(defun c:ma-elev-sect (/ alpha omega) 
  (setq alpha "elev"
        omega "sect"
  )
  (search-ma alpha omega)
)
(defun c:ma-elev-detl (/ alpha omega) 
  (setq alpha "elev"
        omega "detl"
  )
  (search-ma alpha omega)
)
(defun c:ma-elev-plan (/ alpha omega) 
  (setq alpha "elev"
        omega "plan"
  )
  (search-ma alpha omega)
)
(defun c:ma-elev-anno (/ alpha omega) 
  (setq alpha "elev"
        omega "anno"
  )
  (search-ma alpha omega)
)
(defun c:ma-sect-detl (/ alpha omega) 
  (setq alpha "sect"
        omega "detl"
  )
  (search-ma alpha omega)
)
(defun c:ma-sect-detl (/ alpha omega) 
  (setq alpha "sect"
        omega "elev"
  )
  (search-ma alpha omega)
)
(defun c:ma-sect-plan (/ alpha omega) 
  (setq alpha "sect"
        omega "plan"
  )
  (search-ma alpha omega)
)
(defun c:ma-sect-anno (/ alpha omega) 
  (setq alpha "sect"
        omega "anno"
  )
  (search-ma alpha omega)
)
(defun c:ma-detl-sect (/ alpha omega) 
  (setq alpha "detl"
        omega "sect"
  )
  (search-ma alpha omega)
)
(defun c:ma-detl-elev (/ alpha omega) 
  (setq alpha "detl"
        omega "elev"
  )
  (search-ma alpha omega)
)
(defun c:ma-detl-plan (/ alpha omega) 
  (setq alpha "detl"
        omega "plan"
  )
  (search-ma alpha omega)
)
(defun c:ma-detl-anno (/ alpha omega) 
  (setq alpha "detl"
        omega "anno"
  )
  (search-ma alpha omega)
)
(defun c:ma-anno-plan (/ alpha omega) 
  (setq alpha "anno"
        omega "plan"
  )
  (search-ma alpha omega)
)
(defun c:ma-anno-detl (/ alpha omega) 
  (setq alpha "anno"
        omega "detl"
  )
  (search-ma alpha omega)
)
(defun c:ma-anno-sect (/ alpha omega) 
  (setq alpha "anno"
        omega "sect"
  )
  (search-ma alpha omega)
)
(defun c:ma-anno-elev (/ alpha omega) 
  (setq alpha "anno"
        omega "elev"
  )
  (search-ma alpha omega)
)
