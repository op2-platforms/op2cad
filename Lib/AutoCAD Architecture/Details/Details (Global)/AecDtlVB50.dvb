Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit

Public Sub AecDtlCladWallOpen()

    Dim dblPnt(0 To 2) As Double
    Dim blkdef As AcadBlock
    Dim line As AcadLine
    Dim arc As AcadArc
    Dim dblExtThick As Double
    Dim dblCavityThick As Double
    Dim dblWallHeight As Double
    Dim dblStancionClear As Double
    Dim varP1 As Variant
    Dim varP2 As Variant
    Dim dblDepth As Double
    Dim dblTF As Double
    Dim dblHeadHeight As Double
    Dim dblCladThick As Double
    Dim dblCladOffset As Double
    Dim dblSheetRailDepth As Double
    Dim dblSheetRailSpacing As Double
    Dim dblSheetRailThick As Double
    Dim dblTmpWid As Double
    Dim dblSavedWid As Double
    Dim dblFlashingClear As Double
    Dim dblInsLeftOffset As Double
    Dim dblInsRightOffset As Double
    Dim dblInsBottomOffset As Double
    Dim blnRigidHatch As Boolean
    Dim blnInsulationHatch As Boolean
    Dim dblFlashExtension As Double
    Dim dblFlashRad As Double
    Dim dblWallTopClear As Double
    Dim dblHeadExtension As Double
    Dim dblMasonryTop As Double
    Dim dblCladBaseHgt As Double
    Dim dblSoffitOverhang As Double
    Dim dblSoffitThick As Double
    Dim dblWindowHeight As Double
    Dim dblFlashUnder As Double
    Dim dblWallBottomClear As Double

    dblPnt(0) = 0#
    dblPnt(1) = 0#
    dblPnt(2) = 0#
    
    Set blkdef = ThisDrawing.Blocks.Add(dblPnt, "*U")
    
    dblDepth = AecDtlApplication.Database.GetFieldValueDoubleUnitDep("Depth")
    dblTF = AecDtlApplication.Database.GetFieldValueDoubleUnitDep("TF")
    
    dblExtThick = AecDtlApplication.Palette.GetPropertyValueDoubleUnitDep("ExtThick")
    dblCavityThick = AecDtlApplication.Palette.GetPropertyValueDoubleUnitDep("CavityThick")
    dblWallHeight = AecDtlApplication.Palette.GetPropertyValueDoubleUnitDep("WallHeight")
    dblMasonryTop = AecDtlApplication.Palette.GetPropertyValueDoubleUnitDep("MasonryTop")
    dblHeadHeight = AecDtlApplication.Palette.GetPropertyValueDoubleUnitDep("HeadHeight")
    dblCladThick = AecDtlApplication.Palette.GetPropertyValueDoubleUnitDep("CladThick")
    dblCladOffset = AecDtlApplication.Palette.GetPropertyValueDoubleUnitDep("CladOffset")
    dblStancionClear = AecDtlApplication.Palette.GetPropertyValueDoubleUnitDep("StancionClear")
    dblSheetRailDepth = AecDtlApplication.Palette.GetPropertyValueDoubleUnitDep("SheetRailDepth")
    dblSheetRailSpacing = AecDtlApplication.Palette.GetPropertyValueDoubleUnitDep("SheetRailSpacing")
    dblCladBaseHgt = AecDtlApplication.Palette.GetPropertyValueDoubleUnitDep("CladBaseHgt")
    dblSoffitOverhang = AecDtlApplication.Palette.GetPropertyValueDoubleUnitDep("SoffitOverhang")
    dblSoffitThick = AecDtlApplication.Palette.GetPropertyValueDoubleUnitDep("SoffitThick")
    dblWindowHeight = AecDtlApplication.Palette.GetPropertyValueDoubleUnitDep("WindowHeight")
    blnRigidHatch = AecDtlApplication.Palette.GetPropertyValueBool("doRigidHatch")
    blnInsulationHatch = AecDtlApplication.Palette.GetPropertyValueBool("doInsulationHatch")
    
    dblWallTopClear = AecDtlApplication.Recipe.GetDataValueDoubleUnitDep("Values", "WallTopClear")
    dblWallBottomClear = AecDtlApplication.Recipe.GetDataValueDoubleUnitDep("Values", "WallBottomClear")
    dblSheetRailThick = AecDtlApplication.Recipe.GetDataValueDoubleUnitDep("Values", "SheetRailThick")
    dblFlashingClear = AecDtlApplication.Recipe.GetDataValueDoubleUnitDep("Values", "FlashingClear")
    dblInsLeftOffset = AecDtlApplication.Recipe.GetDataValueDoubleUnitDep("Values", "InsLeftOffset")
    dblInsRightOffset = AecDtlApplication.Recipe.GetDataValueDoubleUnitDep("Values", "InsRightOffset")
    dblInsBottomOffset = AecDtlApplication.Recipe.GetDataValueDoubleUnitDep("Values", "InsBottomOffset")
    dblFlashExtension = AecDtlApplication.Recipe.GetDataValueDoubleUnitDep("Values", "FlashExtension")
    dblHeadExtension = AecDtlApplication.Recipe.GetDataValueDoubleUnitDep("Values", "HeadExtension")
    dblFlashRad = AecDtlApplication.Recipe.GetDataValueDoubleUnitDep("Values", "FlashRad")
    dblFlashUnder = AecDtlApplication.Recipe.GetDataValueDoubleUnitDep("Values", "FlashUnder")
    
    varP1 = dblPnt
    varP1(0) = dblExtThick + dblCavityThick - dblStancionClear
    blkdef.InsertBlock varP1, CreateBlock(dblDepth, dblWallHeight, False, "steel", "", , , , False).Name, 1#, 1#, 1#, 0#
    varP1(0) = varP1(0) + dblTF
    blkdef.InsertBlock varP1, CreateBlock(dblDepth - dblTF * 2#, dblWallHeight, False, "steel", "", , False, , False).Name, 1#, 1#, 1#, 0#
    
    varP1 = dblPnt
    varP1(0) = -dblCladOffset
    varP1(1) = dblWallHeight
    blkdef.InsertBlock varP1, CreateUBeam(dblCladOffset + dblExtThick + dblCavityThick - dblStancionClear, dblSheetRailDepth, dblSheetRailThick, dblSheetRailThick, "braces").Name, 1#, -1#, 1#, 0#
    varP1(0) = -dblCladOffset + dblFlashingClear
    varP1(1) = dblHeadHeight
    dblSavedWid = dblCladOffset + dblExtThick + dblCavityThick - dblStancionClear
    dblTmpWid = dblSavedWid - dblFlashingClear
    While varP1(1) <= dblWallHeight - 2# * dblSheetRailDepth
        blkdef.InsertBlock varP1, CreateUBeam(dblTmpWid, dblSheetRailDepth, dblSheetRailThick, dblSheetRailThick, "braces").Name, 1#, 1#, 1#, 0#
        dblTmpWid = dblSavedWid
        varP1(0) = -dblCladOffset
        varP1(1) = varP1(1) + dblSheetRailSpacing
    Wend
    
    varP1 = dblPnt
    varP1(0) = -dblCladOffset - dblCladThick
    varP1(1) = dblHeadHeight + dblWallBottomClear
    blkdef.InsertBlock varP1, CreateBlock(dblCladThick, dblWallHeight - (dblHeadHeight + dblWallBottomClear), False, "steel", "").Name, 1#, 1#, 1#, 0#
    varP1(0) = varP1(0) + dblInsLeftOffset
    varP1(1) = varP1(1) + dblInsBottomOffset
    blkdef.InsertBlock varP1, CreateBlock(dblCladThick - dblInsLeftOffset - dblInsRightOffset, dblWallHeight - (dblHeadHeight + dblWallBottomClear) - dblInsBottomOffset * 2#, blnRigidHatch, "rigidins", "rigidfill").Name, 1#, 1#, 1#, 0#
    
    varP1 = dblPnt
    varP1(0) = -dblCladOffset + dblFlashingClear
    varP1(1) = dblHeadHeight + dblFlashExtension + dblFlashRad
    varP2 = varP1
    varP2(1) = varP2(1) - dblFlashExtension
    Set line = blkdef.AddLine(varP1, varP2)
    AecDtlApplication.Recipe.SetEntityProperties "header", line
    varP2(0) = varP2(0) - dblFlashRad
    Set arc = blkdef.AddArc(varP2, dblFlashRad, Pi * 1.5, 0#)
    AecDtlApplication.Recipe.SetEntityProperties "header", arc
    varP2(1) = varP2(1) - dblFlashRad
    varP1 = varP2
    varP1(0) = -dblCladOffset - dblCladThick - dblHeadExtension + dblFlashRad * 2#
    Set line = blkdef.AddLine(varP1, varP2)
    AecDtlApplication.Recipe.SetEntityProperties "header", line
    varP1(1) = varP1(1) - dblFlashRad * 2#
    Set arc = blkdef.AddArc(varP1, dblFlashRad * 2#, Pi * 0.5, Pi)
    AecDtlApplication.Recipe.SetEntityProperties "header", arc
    varP1(0) = varP1(0) - dblFlashRad * 2#
    varP2 = varP1
    varP2(1) = varP2(1) - (dblHeadExtension - dblFlashRad * 2#)
    Set line = blkdef.AddLine(varP1, varP2)
    AecDtlApplication.Recipe.SetEntityProperties "header", line
    varP1 = varP2
    varP1(0) = varP1(0) + dblFlashRad * 2#
    varP1(1) = varP1(1) + dblFlashRad * 2#
    Set line = blkdef.AddLine(varP1, varP2)
    AecDtlApplication.Recipe.SetEntityProperties "header", line
    varP1(0) = dblExtThick + dblCavityThick - dblStancionClear
    varP1(1) = dblHeadHeight - dblFlashRad
    varP2 = varP1
    varP2(0) = -dblCladOffset - dblCladThick - dblHeadExtension + dblFlashRad * 2#
    Set line = blkdef.AddLine(varP1, varP2)
    AecDtlApplication.Recipe.SetEntityProperties "header", line
    varP2(1) = varP2(1) - dblFlashRad
    Set arc = blkdef.AddArc(varP2, dblFlashRad, Pi * 0.5, Pi)
    AecDtlApplication.Recipe.SetEntityProperties "header", arc
    varP2(0) = varP2(0) - dblFlashRad
    varP1 = varP2
    varP1(1) = varP1(1) - dblHeadExtension + dblFlashRad * 4#
    Set line = blkdef.AddLine(varP1, varP2)
    AecDtlApplication.Recipe.SetEntityProperties "header", line

    varP1 = dblPnt
    varP1(0) = -dblCladOffset
    varP1(1) = dblHeadHeight - dblWindowHeight
    blkdef.InsertBlock varP1, CreateUBeam(dblCladOffset + dblExtThick + dblCavityThick - dblStancionClear, dblSheetRailDepth, dblSheetRailThick, dblSheetRailThick, "braces").Name, 1#, -1#, 1#, 0#
    varP1(0) = -dblCladOffset + dblFlashingClear
    varP1(1) = dblMasonryTop + dblWallTopClear
    blkdef.InsertBlock varP1, CreateUBeam(dblCladOffset + dblExtThick + dblCavityThick - dblStancionClear - dblFlashingClear, dblSheetRailDepth, dblSheetRailThick, dblSheetRailThick, "braces").Name, 1#, 1#, 1#, 0#
    
    varP1 = dblPnt
    varP1(0) = -dblCladOffset - dblCladThick
    varP1(1) = dblCladBaseHgt
    blkdef.InsertBlock varP1, CreateBlock(dblCladThick, dblHeadHeight - dblCladBaseHgt - dblWindowHeight, False, "steel", "").Name, 1#, 1#, 1#, 0#
    varP1(0) = varP1(0) + dblInsLeftOffset
    varP1(1) = varP1(1) + dblInsBottomOffset
    blkdef.InsertBlock varP1, CreateBlock(dblCladThick - dblInsLeftOffset - dblInsRightOffset, dblHeadHeight - dblCladBaseHgt - dblWindowHeight - dblInsBottomOffset * 2#, blnRigidHatch, "rigidins", "rigidfill").Name, 1#, 1#, 1#, 0#
    
    varP1 = dblPnt
    varP1(0) = -dblCladOffset + dblFlashingClear
    varP1(1) = dblCladBaseHgt + dblFlashExtension
    varP2 = varP1
    varP2(1) = varP2(1) - dblFlashExtension
    Set line = blkdef.AddLine(varP1, varP2)
    AecDtlApplication.Recipe.SetEntityProperties "soffit", line
    varP2(0) = varP2(0) - dblFlashRad
    Set arc = blkdef.AddArc(varP2, dblFlashRad, Pi * 1.5, 0#)
    AecDtlApplication.Recipe.SetEntityProperties "soffit", arc
    varP2(1) = varP2(1) - dblFlashRad
    varP1 = varP2
    varP1(0) = -dblCladOffset - dblCladThick - dblSoffitOverhang + dblFlashRad
    Set line = blkdef.AddLine(varP1, varP2)
    AecDtlApplication.Recipe.SetEntityProperties "soffit", line
    varP1(1) = varP1(1) - dblFlashRad
    Set arc = blkdef.AddArc(varP1, dblFlashRad, Pi * 0.5, Pi)
    AecDtlApplication.Recipe.SetEntityProperties "soffit", arc
    varP1(0) = varP1(0) - dblFlashRad
    varP2 = varP1
    varP2(1) = varP2(1) - (dblSoffitThick - dblFlashRad * 2#)
    Set line = blkdef.AddLine(varP1, varP2)
    AecDtlApplication.Recipe.SetEntityProperties "soffit", line
    If blnInsulationHatch Then
        blkdef.InsertBlock varP2, CreateInsulation(dblSoffitOverhang + dblCladThick + dblCladOffset - dblFlashRad, dblSoffitThick - 2# * dblFlashRad, "insulation", "", False, False).Name, 1#, 1#, 1#, -Pi * 0.5
    End If
    varP2(0) = varP2(0) + dblFlashRad
    Set arc = blkdef.AddArc(varP2, dblFlashRad, Pi, Pi * 1.5)
    AecDtlApplication.Recipe.SetEntityProperties "soffit", arc
    varP1 = varP2
    varP1(0) = varP1(0) + dblSoffitOverhang + dblCladThick + dblCladOffset - dblFlashRad * 3#
    Set line = blkdef.AddLine(varP1, varP2)
    AecDtlApplication.Recipe.SetEntityProperties "soffit", line
    varP2(1) = varP2(1) - dblFlashRad
    varP1 = varP2
    varP1(0) = varP1(0) + dblFlashUnder - dblFlashRad
    Set line = blkdef.AddLine(varP1, varP2)
    AecDtlApplication.Recipe.SetEntityProperties "soffit", line
    varP1 = dblPnt
    varP1(0) = -dblFlashRad
    varP1(1) = dblCladBaseHgt - dblFlashRad * 2#
    varP2 = varP1
    varP2(1) = varP2(1) - dblSoffitThick + dblFlashRad * 2#
    Set line = blkdef.AddLine(varP1, varP2)
    AecDtlApplication.Recipe.SetEntityProperties "soffit", line
    varP2(0) = varP2(0) - dblFlashRad
    Set arc = blkdef.AddArc(varP2, dblFlashRad, Pi * -0.5, 0#)
    AecDtlApplication.Recipe.SetEntityProperties "soffit", arc
    varP2(1) = varP2(1) - dblFlashRad
    varP1 = varP2
    varP1(0) = varP1(0) - dblFlashUnder + dblFlashRad
    Set line = blkdef.AddLine(varP1, varP2)
    AecDtlApplication.Recipe.SetEntityProperties "soffit", line
    
    varP1 = dblPnt
    varP1(0) = dblExtThick + dblCavityThick - dblStancionClear
    varP1(1) = dblHeadHeight - dblWindowHeight + dblFlashRad
    varP2 = varP1
    varP2(0) = -dblCladOffset - dblCladThick - dblHeadExtension + dblFlashRad
    Set line = blkdef.AddLine(varP1, varP2)
    AecDtlApplication.Recipe.SetEntityProperties "soffit", line
    varP2(1) = varP2(1) - dblFlashRad
    Set arc = blkdef.AddArc(varP2, dblFlashRad, Pi * 0.5, Pi)
    AecDtlApplication.Recipe.SetEntityProperties "soffit", arc
    varP2(0) = varP2(0) - dblFlashRad
    varP1 = varP2
    varP1(1) = varP1(1) - dblHeadExtension * 3# + dblFlashRad
    Set line = blkdef.AddLine(varP1, varP2)
    AecDtlApplication.Recipe.SetEntityProperties "soffit", line
    varP1(0) = varP1(0) + dblFlashRad
    Set arc = blkdef.AddArc(varP1, dblFlashRad, Pi, Pi * 1.5)
    AecDtlApplication.Recipe.SetEntityProperties "soffit", arc
    varP1(1) = varP1(1) - dblFlashRad
    varP2 = varP1
    varP2(0) = varP2(0) + dblHeadExtension - dblFlashRad * 3#
    Set line = blkdef.AddLine(varP1, varP2)
    AecDtlApplication.Recipe.SetEntityProperties "soffit", line
    varP2(1) = varP2(1) - dblFlashRad
    Set arc = blkdef.AddArc(varP2, dblFlashRad, 0#, Pi * 0.5)
    AecDtlApplication.Recipe.SetEntityProperties "soffit", arc
    varP2(0) = varP2(0) + dblFlashRad
    varP1 = varP2
    varP1(1) = varP1(1) - dblHeadExtension + dblFlashRad
    Set line = blkdef.AddLine(varP1, varP2)
    AecDtlApplication.Recipe.SetEntityProperties "soffit", line
    
    
    ' start the jig
    Dim status As AecDtlPromptStatus
    status = AecDtlApplication.jig.StampBlock(blkdef)

    ' return the status
    AecDtlApplication.Recipe.ReturnStatus = status

End Sub
Public Sub AecDtlCladWallAboveOpen()

    Dim dblPnt(0 To 2) As Double
    Dim blkdef As AcadBlock
    Dim line As AcadLine
    Dim arc As AcadArc
    Dim dblExtThick As Double
    Dim dblCavityThick As Double
    Dim dblWallHeight As Double
    Dim dblStancionClear As Double
    Dim varP1 As Variant
    Dim varP2 As Variant
    Dim dblDepth As Double
    Dim dblTF As Double
    Dim dblHeadHeight As Double
    Dim dblCladThick As Double
    Dim dblCladOffset As Double
    Dim dblSheetRailDepth As Double
    Dim dblSheetRailSpacing As Double
    Dim dblSheetRailThick As Double
    Dim dblTmpWid As Double
    Dim dblSavedWid As Double
    Dim dblFlashingClear As Double
    Dim dblInsLeftOffset As Double
    Dim dblInsRightOffset As Double
    Dim dblInsBottomOffset As Double
    Dim blnRigidHatch As Boolean
    Dim dblFlashExtension As Double
    Dim dblFlashRad As Double
    Dim dblWallTopClear As Double
    Dim dblHeadExtension As Double

    dblPnt(0) = 0#
    dblPnt(1) = 0#
    dblPnt(2) = 0#
    
    Set blkdef = ThisDrawing.Blocks.Add(dblPnt, "*U")
    
    dblDepth = AecDtlApplication.Database.GetFieldValueDoubleUnitDep("Depth")
    dblTF = AecDtlApplication.Database.GetFieldValueDoubleUnitDep("TF")
    
    dblExtThick = AecDtlApplication.Palette.GetPropertyValueDoubleUnitDep("ExtThick")
    dblCavityThick = AecDtlApplication.Palette.GetPropertyValueDoubleUnitDep("CavityThick")
    dblWallHeight = AecDtlApplication.Palette.GetPropertyValueDoubleUnitDep("WallHeight")
    dblHeadHeight = AecDtlApplication.Palette.GetPropertyValueDoubleUnitDep("HeadHeight")
    dblCladThick = AecDtlApplication.Palette.GetPropertyValueDoubleUnitDep("CladThick")
    dblCladOffset = AecDtlApplication.Palette.GetPropertyValueDoubleUnitDep("CladOffset")
    dblStancionClear = AecDtlApplication.Palette.GetPropertyValueDoubleUnitDep("StancionClear")
    dblSheetRailDepth = AecDtlApplication.Palette.GetPropertyValueDoubleUnitDep("SheetRailDepth")
    dblSheetRailSpacing = AecDtlApplication.Palette.GetPropertyValueDoubleUnitDep("SheetRailSpacing")
    blnRigidHatch = AecDtlApplication.Palette.GetPropertyValueBool("doRigidHatch")
    
    dblWallTopClear = AecDtlApplication.Recipe.GetDataValueDoubleUnitDep("Values", "WallTopClear")
    dblSheetRailThick = AecDtlApplication.Recipe.GetDataValueDoubleUnitDep("Values", "SheetRailThick")
    dblFlashingClear = AecDtlApplication.Recipe.GetDataValueDoubleUnitDep("Values", "FlashingClear")
    dblInsLeftOffset = AecDtlApplication.Recipe.GetDataValueDoubleUnitDep("Values", "InsLeftOffset")
    dblInsRightOffset = AecDtlApplication.Recipe.GetDataValueDoubleUnitDep("Values", "InsRightOffset")
    dblInsBottomOffset = AecDtlApplication.Recipe.GetDataValueDoubleUnitDep("Values", "InsBottomOffset")
    dblFlashExtension = AecDtlApplication.Recipe.GetDataValueDoubleUnitDep("Values", "FlashExtension")
    dblHeadExtension = AecDtlApplication.Recipe.GetDataValueDoubleUnitDep("Values", "HeadExtension")
    dblFlashRad = AecDtlApplication.Recipe.GetDataValueDoubleUnitDep("Values", "FlashRad")
    
    varP1 = dblPnt
    varP1(0) = dblExtThick + dblCavityThick - dblStancionClear
    blkdef.InsertBlock varP1, CreateBlock(dblDepth, dblWallHeight, False, "steel", "", , , , False).Name, 1#, 1#, 1#, 0#
    varP1(0) = varP1(0) + dblTF
    blkdef.InsertBlock varP1, CreateBlock(dblDepth - dblTF * 2#, dblWallHeight, False, "steel", "", , False, , False).Name, 1#, 1#, 1#, 0#
    
    varP1 = dblPnt
    varP1(0) = -dblCladOffset
    varP1(1) = dblWallHeight
    blkdef.InsertBlock varP1, CreateUBeam(dblCladOffset + dblExtThick + dblCavityThick - dblStancionClear, dblSheetRailDepth, dblSheetRailThick, dblSheetRailThick, "braces").Name, 1#, -1#, 1#, 0#
    varP1(0) = -dblCladOffset + dblFlashingClear
    varP1(1) = dblHeadHeight
    dblSavedWid = dblCladOffset + dblExtThick + dblCavityThick - dblStancionClear
    dblTmpWid = dblSavedWid - dblFlashingClear
    While varP1(1) <= dblWallHeight - 2# * dblSheetRailDepth
        blkdef.InsertBlock varP1, CreateUBeam(dblTmpWid, dblSheetRailDepth, dblSheetRailThick, dblSheetRailThick, "braces").Name, 1#, 1#, 1#, 0#
        dblTmpWid = dblSavedWid
        varP1(0) = -dblCladOffset
        varP1(1) = varP1(1) + dblSheetRailSpacing
    Wend
    varP1(0) = dblExtThick + dblCavityThick - dblStancionClear + dblTF
    varP1(1) = dblHeadHeight
    blkdef.InsertBlock varP1, CreateUBeam(dblDepth - dblTF * 2#, dblSheetRailDepth, dblSheetRailThick, dblSheetRailThick, "braces").Name, 1#, 1#, 1#, 0#
    
    varP1 = dblPnt
    varP1(0) = -dblCladOffset - dblCladThick
    varP1(1) = dblHeadHeight + dblWallTopClear
    blkdef.InsertBlock varP1, CreateBlock(dblCladThick, dblWallHeight - (dblHeadHeight + dblWallTopClear), False, "steel", "").Name, 1#, 1#, 1#, 0#
    varP1(0) = varP1(0) + dblInsLeftOffset
    varP1(1) = varP1(1) + dblInsBottomOffset
    blkdef.InsertBlock varP1, CreateBlock(dblCladThick - dblInsLeftOffset - dblInsRightOffset, dblWallHeight - (dblHeadHeight + dblWallTopClear) - dblInsBottomOffset * 2#, blnRigidHatch, "rigidins", "rigidfill").Name, 1#, 1#, 1#, 0#
    
    varP1 = dblPnt
    varP1(0) = -dblCladOffset + dblFlashingClear
    varP1(1) = dblHeadHeight + dblFlashExtension + dblFlashRad
    varP2 = varP1
    varP2(1) = varP2(1) - dblFlashExtension
    Set line = blkdef.AddLine(varP1, varP2)
    AecDtlApplication.Recipe.SetEntityProperties "header", line
    varP2(0) = varP2(0) - dblFlashRad
    Set arc = blkdef.AddArc(varP2, dblFlashRad, Pi * 1.5, 0#)
    AecDtlApplication.Recipe.SetEntityProperties "header", arc
    varP2(1) = varP2(1) - dblFlashRad
    varP1 = varP2
    varP1(0) = -dblCladOffset - dblCladThick - dblHeadExtension + dblFlashRad * 2#
    Set line = blkdef.AddLine(varP1, varP2)
    AecDtlApplication.Recipe.SetEntityProperties "header", line
    varP1(1) = varP1(1) - dblFlashRad * 2#
    Set arc = blkdef.AddArc(varP1, dblFlashRad * 2#, Pi * 0.5, Pi)
    AecDtlApplication.Recipe.SetEntityProperties "header", arc
    varP1(0) = varP1(0) - dblFlashRad * 2#
    varP2 = varP1
    varP2(1) = varP2(1) - (dblHeadExtension - dblFlashRad * 2#)
    Set line = blkdef.AddLine(varP1, varP2)
    AecDtlApplication.Recipe.SetEntityProperties "header", line
    varP1 = varP2
    varP1(0) = varP1(0) + dblFlashRad * 2#
    varP1(1) = varP1(1) + dblFlashRad * 2#
    Set line = blkdef.AddLine(varP1, varP2)
    AecDtlApplication.Recipe.SetEntityProperties "header", line
    varP1(0) = dblExtThick + dblCavityThick - dblStancionClear
    varP1(1) = dblHeadHeight - dblFlashRad
    varP2 = varP1
    varP2(0) = -dblCladOffset - dblCladThick - dblHeadExtension + dblFlashRad * 2#
    Set line = blkdef.AddLine(varP1, varP2)
    AecDtlApplication.Recipe.SetEntityProperties "header", line
    varP2(1) = varP2(1) - dblFlashRad
    Set arc = blkdef.AddArc(varP2, dblFlashRad, Pi * 0.5, Pi)
    AecDtlApplication.Recipe.SetEntityProperties "header", arc
    varP2(0) = varP2(0) - dblFlashRad
    varP1 = varP2
    varP1(1) = varP1(1) - dblHeadExtension + dblFlashRad * 4#
    Set line = blkdef.AddLine(varP1, varP2)
    AecDtlApplication.Recipe.SetEntityProperties "header", line

    ' start the jig
    Dim status As AecDtlPromptStatus
    status = AecDtlApplication.jig.StampBlock(blkdef)

    ' return the status
    AecDtlApplication.Recipe.ReturnStatus = status

End Sub
Public Sub AecDtlAecDtlCladWall()

    Dim dblPnt(0 To 2) As Double
    Dim blkdef As AcadBlock
    Dim line As AcadLine
    Dim arc As AcadArc
    Dim dblExtThick As Double
    Dim dblCavityThick As Double
    Dim dblWallHeight As Double
    Dim dblStancionClear As Double
    Dim varP1 As Variant
    Dim varP2 As Variant
    Dim dblDepth As Double
    Dim dblTF As Double
    Dim dblMasonryTop As Double
    Dim dblCladThick As Double
    Dim dblCladOffset As Double
    Dim dblCladBaseHgt As Double
    Dim dblSheetRailDepth As Double
    Dim dblSheetRailSpacing As Double
    Dim dblSoffitOverhang As Double
    Dim dblSoffitThick As Double
    Dim dblWallTopClear As Double
    Dim dblSheetRailThick As Double
    Dim dblTmpWid As Double
    Dim dblSavedWid As Double
    Dim dblFlashingClear As Double
    Dim dblInsLeftOffset As Double
    Dim dblInsRightOffset As Double
    Dim dblInsBottomOffset As Double
    Dim blnRigidHatch As Boolean
    Dim blnInsulationHatch As Boolean
    Dim dblFlashExtension As Double
    Dim dblFlashRad As Double
    Dim dblFlashUnder As Double

    dblPnt(0) = 0#
    dblPnt(1) = 0#
    dblPnt(2) = 0#
    
    Set blkdef = ThisDrawing.Blocks.Add(dblPnt, "*U")
    
    dblDepth = AecDtlApplication.Database.GetFieldValueDoubleUnitDep("Depth")
    dblTF = AecDtlApplication.Database.GetFieldValueDoubleUnitDep("TF")
    
    dblExtThick = AecDtlApplication.Palette.GetPropertyValueDoubleUnitDep("ExtThick")
    dblCavityThick = AecDtlApplication.Palette.GetPropertyValueDoubleUnitDep("CavityThick")
    dblWallHeight = AecDtlApplication.Palette.GetPropertyValueDoubleUnitDep("WallHeight")
    dblMasonryTop = AecDtlApplication.Palette.GetPropertyValueDoubleUnitDep("MasonryTop")
    dblCladThick = AecDtlApplication.Palette.GetPropertyValueDoubleUnitDep("CladThick")
    dblCladOffset = AecDtlApplication.Palette.GetPropertyValueDoubleUnitDep("CladOffset")
    dblCladBaseHgt = AecDtlApplication.Palette.GetPropertyValueDoubleUnitDep("CladBaseHgt")
    dblStancionClear = AecDtlApplication.Palette.GetPropertyValueDoubleUnitDep("StancionClear")
    dblSheetRailDepth = AecDtlApplication.Palette.GetPropertyValueDoubleUnitDep("SheetRailDepth")
    dblSheetRailSpacing = AecDtlApplication.Palette.GetPropertyValueDoubleUnitDep("SheetRailSpacing")
    dblSoffitOverhang = AecDtlApplication.Palette.GetPropertyValueDoubleUnitDep("SoffitOverhang")
    dblSoffitThick = AecDtlApplication.Palette.GetPropertyValueDoubleUnitDep("SoffitThick")
    blnRigidHatch = AecDtlApplication.Palette.GetPropertyValueBool("doRigidHatch")
    blnInsulationHatch = AecDtlApplication.Palette.GetPropertyValueBool("doInsulationHatch")
    
    dblWallTopClear = AecDtlApplication.Recipe.GetDataValueDoubleUnitDep("Values", "WallTopClear")
    dblSheetRailThick = AecDtlApplication.Recipe.GetDataValueDoubleUnitDep("Values", "SheetRailThick")
    dblFlashingClear = AecDtlApplication.Recipe.GetDataValueDoubleUnitDep("Values", "FlashingClear")
    dblInsLeftOffset = AecDtlApplication.Recipe.GetDataValueDoubleUnitDep("Values", "InsLeftOffset")
    dblInsRightOffset = AecDtlApplication.Recipe.GetDataValueDoubleUnitDep("Values", "InsRightOffset")
    dblInsBottomOffset = AecDtlApplication.Recipe.GetDataValueDoubleUnitDep("Values", "InsBottomOffset")
    dblFlashExtension = AecDtlApplication.Recipe.GetDataValueDoubleUnitDep("Values", "FlashExtension")
    dblFlashRad = AecDtlApplication.Recipe.GetDataValueDoubleUnitDep("Values", "FlashRad")
    dblFlashUnder = AecDtlApplication.Recipe.GetDataValueDoubleUnitDep("Values", "FlashUnder")
    
    varP1 = dblPnt
    varP1(0) = dblExtThick + dblCavityThick - dblStancionClear
    blkdef.InsertBlock varP1, CreateBlock(dblDepth, dblWallHeight, False, "steel", "", , , , False).Name, 1#, 1#, 1#, 0#
    varP1(0) = varP1(0) + dblTF
    blkdef.InsertBlock varP1, CreateBlock(dblDepth - dblTF * 2#, dblWallHeight, False, "steel", "", , False, , False).Name, 1#, 1#, 1#, 0#
    
    varP1 = dblPnt
    varP1(0) = -dblCladOffset
    varP1(1) = dblWallHeight
    blkdef.InsertBlock varP1, CreateUBeam(dblCladOffset + dblExtThick + dblCavityThick - dblStancionClear, dblSheetRailDepth, dblSheetRailThick, dblSheetRailThick, "braces").Name, 1#, -1#, 1#, 0#
    varP1(0) = -dblCladOffset + dblFlashingClear
    varP1(1) = dblMasonryTop + dblWallTopClear
    dblSavedWid = dblCladOffset + dblExtThick + dblCavityThick - dblStancionClear
    dblTmpWid = dblSavedWid - dblFlashingClear
    While varP1(1) <= dblWallHeight - 2# * dblSheetRailDepth
        blkdef.InsertBlock varP1, CreateUBeam(dblTmpWid, dblSheetRailDepth, dblSheetRailThick, dblSheetRailThick, "braces").Name, 1#, 1#, 1#, 0#
        dblTmpWid = dblSavedWid
        varP1(0) = -dblCladOffset
        varP1(1) = varP1(1) + dblSheetRailSpacing
    Wend
    
    varP1 = dblPnt
    varP1(0) = -dblCladOffset - dblCladThick
    varP1(1) = dblCladBaseHgt
    blkdef.InsertBlock varP1, CreateBlock(dblCladThick, dblWallHeight - dblCladBaseHgt, False, "steel", "").Name, 1#, 1#, 1#, 0#
    varP1(0) = varP1(0) + dblInsLeftOffset
    varP1(1) = varP1(1) + dblInsBottomOffset
    blkdef.InsertBlock varP1, CreateBlock(dblCladThick - dblInsLeftOffset - dblInsRightOffset, dblWallHeight - dblCladBaseHgt - dblInsBottomOffset * 2#, blnRigidHatch, "rigidins", "rigidfill").Name, 1#, 1#, 1#, 0#
    
    varP1 = dblPnt
    varP1(0) = -dblCladOffset + dblFlashingClear
    varP1(1) = dblCladBaseHgt + dblFlashExtension
    varP2 = varP1
    varP2(1) = varP2(1) - dblFlashExtension
    Set line = blkdef.AddLine(varP1, varP2)
    AecDtlApplication.Recipe.SetEntityProperties "soffit", line
    varP2(0) = varP2(0) - dblFlashRad
    Set arc = blkdef.AddArc(varP2, dblFlashRad, Pi * 1.5, 0#)
    AecDtlApplication.Recipe.SetEntityProperties "soffit", arc
    varP2(1) = varP2(1) - dblFlashRad
    varP1 = varP2
    varP1(0) = -dblCladOffset - dblCladThick - dblSoffitOverhang + dblFlashRad
    Set line = blkdef.AddLine(varP1, varP2)
    AecDtlApplication.Recipe.SetEntityProperties "soffit", line
    varP1(1) = varP1(1) - dblFlashRad
    Set arc = blkdef.AddArc(varP1, dblFlashRad, Pi * 0.5, Pi)
    AecDtlApplication.Recipe.SetEntityProperties "soffit", arc
    varP1(0) = varP1(0) - dblFlashRad
    varP2 = varP1
    varP2(1) = varP2(1) - (dblSoffitThick - dblFlashRad * 2#)
    Set line = blkdef.AddLine(varP1, varP2)
    AecDtlApplication.Recipe.SetEntityProperties "soffit", line
    If blnInsulationHatch Then
        blkdef.InsertBlock varP2, CreateInsulation(dblSoffitOverhang + dblCladThick + dblCladOffset - dblFlashRad, dblSoffitThick - 2# * dblFlashRad, "insulation", "", False, False).Name, 1#, 1#, 1#, -Pi * 0.5
    End If
    varP2(0) = varP2(0) + dblFlashRad
    Set arc = blkdef.AddArc(varP2, dblFlashRad, Pi, Pi * 1.5)
    AecDtlApplication.Recipe.SetEntityProperties "soffit", arc
    varP1 = varP2
    varP1(0) = varP1(0) + dblSoffitOverhang + dblCladThick + dblCladOffset - dblFlashRad * 3#
    Set line = blkdef.AddLine(varP1, varP2)
    AecDtlApplication.Recipe.SetEntityProperties "soffit", line
    varP2(1) = varP2(1) - dblFlashRad
    varP1 = varP2
    varP1(0) = varP1(0) + dblFlashUnder - dblFlashRad
    Set line = blkdef.AddLine(varP1, varP2)
    AecDtlApplication.Recipe.SetEntityProperties "soffit", line
    varP1 = dblPnt
    varP1(0) = -dblFlashRad
    varP1(1) = dblCladBaseHgt - dblFlashRad * 2#
    varP2 = varP1
    varP2(1) = varP2(1) - dblSoffitThick + dblFlashRad * 2#
    Set line = blkdef.AddLine(varP1, varP2)
    AecDtlApplication.Recipe.SetEntityProperties "soffit", line
    varP2(0) = varP2(0) - dblFlashRad
    Set arc = blkdef.AddArc(varP2, dblFlashRad, Pi * -0.5, 0#)
    AecDtlApplication.Recipe.SetEntityProperties "soffit", arc
    varP2(1) = varP2(1) - dblFlashRad
    varP1 = varP2
    varP1(0) = varP1(0) - dblFlashUnder + dblFlashRad
    Set line = blkdef.AddLine(varP1, varP2)
    AecDtlApplication.Recipe.SetEntityProperties "soffit", line

    ' start the jig
    Dim status As AecDtlPromptStatus
    status = AecDtlApplication.jig.StampBlock(blkdef)

    ' return the status
    AecDtlApplication.Recipe.ReturnStatus = status

End Sub
Public Sub AecDtlRidgeTileSection()

    Dim dblPnt(0 To 2) As Double
    Dim blkdef As AcadBlock
    Dim dblAng As Double
    Dim dblWidth As Double
    Dim dblThick As Double
    Dim varP1 As Variant
    Dim varP2 As Variant
    Dim varP3 As Variant
    Dim varP4 As Variant
    Dim line As AcadLine

    dblPnt(0) = 0#
    dblPnt(1) = 0#
    dblPnt(2) = 0#
    
    Set blkdef = ThisDrawing.Blocks.Add(dblPnt, "*U")

    dblAng = AecDtlApplication.Database.GetFieldValueDouble("Angle")
    dblWidth = AecDtlApplication.Database.GetFieldValueDoubleUnitDep("Width")
    dblThick = AecDtlApplication.Database.GetFieldValueDoubleUnitDep("Thickness")
    
    varP1 = dblPnt
    varP1(1) = dblThick / Sin((0.5 * dblAng) * DegToRad)
    varP2 = CDLPolar(varP1, Pi + (180# - dblAng) * 0.5 * DegToRad, (dblWidth * 0.5) / Cos((180# - dblAng) * 0.5 * DegToRad))
    
    varP3 = dblPnt
    varP4 = CDLPolar(varP3, Pi + (180# - dblAng) * 0.5 * DegToRad, (dblWidth * 0.5) / Cos((180# - dblAng) * 0.5 * DegToRad))
    
    Set line = blkdef.AddLine(varP1, varP2)
    AecDtlApplication.Recipe.SetEntityProperties "tile", line
    Set line = blkdef.AddLine(varP3, varP4)
    AecDtlApplication.Recipe.SetEntityProperties "tile", line
    Set line = blkdef.AddLine(varP2, varP4)
    AecDtlApplication.Recipe.SetEntityProperties "tile", line
    
    varP2(0) = -varP2(0)
    varP4(0) = -varP4(0)

    Set line = blkdef.AddLine(varP1, varP2)
    AecDtlApplication.Recipe.SetEntityProperties "tile", line
    Set line = blkdef.AddLine(varP3, varP4)
    AecDtlApplication.Recipe.SetEntityProperties "tile", line
    Set line = blkdef.AddLine(varP2, varP4)
    AecDtlApplication.Recipe.SetEntityProperties "tile", line

    ' start the jig
    Dim status As AecDtlPromptStatus
    status = AecDtlApplication.jig.StampBlock(blkdef)

    ' return the status
    AecDtlApplication.Recipe.ReturnStatus = status

End Sub
Public Sub AecDtlFlatTileSection()

    Dim dblTileLen As Double
    Dim dblTileThick As Double
    Dim dblHeadLap As Double
    Dim dblLipThick As Double
    Dim dblLipOver As Double
    Dim dblFactor As Double
    Dim dblBatWid As Double
    Dim dblBatDep As Double
    Dim dblPnt(0 To 2) As Double
    Dim blkdef1 As AcadBlock
    Dim blkdef2 As AcadBlock
    Dim blkdef3 As AcadBlock
    Dim dblStep As Double
    Dim dblGap As Double
    Dim dblTileAng As Double
    Dim varP1 As Variant
    Dim varP2 As Variant
    Dim varP3 As Variant
    Dim varP4 As Variant
    Dim varP5 As Variant
    Dim varP6 As Variant
    Dim varP7 As Variant
    Dim varP8 As Variant
    Dim varP9 As Variant
    Dim line As AcadLine
    
    dblPnt(0) = 0#
    dblPnt(1) = 0#
    dblPnt(2) = 0#
    
    Set blkdef1 = ThisDrawing.Blocks.Add(dblPnt, "*U")
    Set blkdef2 = ThisDrawing.Blocks.Add(dblPnt, "*U")
    Set blkdef3 = ThisDrawing.Blocks.Add(dblPnt, "*U")
    
    dblTileLen = AecDtlApplication.Palette.GetPropertyValueDoubleUnitDep("TileLen")
    dblTileThick = AecDtlApplication.Palette.GetPropertyValueDoubleUnitDep("TileThick")
    dblHeadLap = AecDtlApplication.Palette.GetPropertyValueDoubleUnitDep("HeadLap")
    dblLipThick = 0#
    dblLipOver = AecDtlApplication.Palette.GetPropertyValueDoubleUnitDep("LipOver")
    dblFactor = AecDtlApplication.Recipe.GetDataValueDoubleUnitDep("Values", "Factor")
    dblBatWid = AecDtlApplication.Recipe.GetDataValueDoubleUnitDep("Values", "BatWid")
    dblBatDep = AecDtlApplication.Recipe.GetDataValueDoubleUnitDep("Values", "BatDep")

    dblStep = Sqr((dblTileThick * dblTileThick) + ((dblTileLen - dblHeadLap) * (dblTileLen - dblHeadLap)))
    dblTileAng = Atn(dblTileThick / (dblTileLen - dblHeadLap))
    dblGap = dblLipOver * Tan(dblTileAng)
        
    varP1 = dblPnt
    varP1(0) = dblStep * 0.5
    varP1(1) = dblBatDep
    blkdef2.InsertBlock varP1, CreateTimberSection(dblBatWid, dblBatDep, "batten").Name, 1#, 1#, 1#, 0#
    blkdef3.InsertBlock varP1, CreateTimberSection(dblBatWid, dblBatDep, "batten").Name, 1#, 1#, 1#, 0#
    
    varP2 = varP1
    varP2(0) = varP2(0) + dblBatWid
    varP3 = CDLPolar(varP2, -dblTileAng, dblGap)
    varP2 = CDLPolar(varP3, Pi - dblTileAng, dblTileLen - dblLipThick)
    
    CDLIntLineLine varP2, varP3, Array(0#, 0#, 0#), Array(0#, 1#, 0#), varP4
    
    varP5 = varP4
    varP6 = varP2
    varP5(0) = varP5(0) + Abs(varP2(0))
    varP6(0) = varP6(0) + Abs(varP2(0))
    Set line = blkdef1.AddLine(varP5, varP6)
    AecDtlApplication.Recipe.SetEntityProperties "tile", line
    varP7 = CDLPolar(varP6, Pi * 0.5 - dblTileAng, dblTileThick)
    Set line = blkdef1.AddLine(varP6, varP7)
    AecDtlApplication.Recipe.SetEntityProperties "tile", line
    varP8 = CDLPolar(varP7, -dblTileAng, dblTileLen)
    CDLIntLineLine varP7, varP8, Array(varP5(0), 0#, 0#), Array(varP5(0), 1#, 0#), varP9
    Set line = blkdef1.AddLine(varP7, varP9)
    AecDtlApplication.Recipe.SetEntityProperties "tile", line
    
    Set line = blkdef2.AddLine(varP4, varP3)
    AecDtlApplication.Recipe.SetEntityProperties "tile", line
    varP5 = CDLPolar(varP3, -Pi * 0.5 - dblTileAng, dblLipThick)
    Set line = blkdef2.AddLine(varP3, varP5)
    AecDtlApplication.Recipe.SetEntityProperties "tile", line
    varP6 = CDLPolar(varP5, -dblTileAng, dblLipOver)
    Set line = blkdef2.AddLine(varP5, varP6)
    AecDtlApplication.Recipe.SetEntityProperties "tile", line
    varP7 = CDLPolar(varP6, Pi * 0.5 - dblTileAng, dblLipThick + dblTileThick)
    Set line = blkdef2.AddLine(varP6, varP7)
    AecDtlApplication.Recipe.SetEntityProperties "tile", line
    varP8 = CDLPolar(varP7, Pi - dblTileAng, dblTileLen)
    CDLIntLineLine varP7, varP8, Array(0#, 0#, 0#), Array(0#, 1#, 0#), varP9
    Set line = blkdef2.AddLine(varP7, varP9)
    AecDtlApplication.Recipe.SetEntityProperties "tile", line
    
    Set line = blkdef3.AddLine(varP4, varP3)
    AecDtlApplication.Recipe.SetEntityProperties "tile", line
    Set line = blkdef3.AddLine(varP3, varP5)
    AecDtlApplication.Recipe.SetEntityProperties "tile", line
    Set line = blkdef3.AddLine(varP5, varP6)
    AecDtlApplication.Recipe.SetEntityProperties "tile", line
    Set line = blkdef3.AddLine(varP6, varP7)
    AecDtlApplication.Recipe.SetEntityProperties "tile", line
    Set line = blkdef3.AddLine(varP7, varP9)
    AecDtlApplication.Recipe.SetEntityProperties "tile", line
    
    varP8 = CDLPolar(varP7, -dblTileAng, dblTileLen)
    CDLIntLineLine varP7, varP8, Array(dblStep, 0#, 0#), Array(dblStep, 1#, 0#), varP6
    Set line = blkdef2.AddLine(varP7, varP6)
    AecDtlApplication.Recipe.SetEntityProperties "tile", line
    varP8 = CDLPolar(varP7, Pi - dblTileAng, dblHeadLap)
    varP6 = CDLPolar(varP8, Pi * 0.5 - dblTileAng, dblTileThick)
    Set line = blkdef2.AddLine(varP8, varP6)
    AecDtlApplication.Recipe.SetEntityProperties "tile", line
    varP8 = CDLPolar(varP6, -dblTileAng, dblHeadLap)
    CDLIntLineLine varP6, varP8, Array(dblStep, 0#, 0#), Array(dblStep, 1#, 0#), varP7
    Set line = blkdef2.AddLine(varP7, varP6)
    AecDtlApplication.Recipe.SetEntityProperties "tile", line
    
    
    ' start the jig
    Dim status As AecDtlPromptStatus
    status = AecDtlApplication.jig.BookendsBlock(blkdef1, blkdef3, blkdef2)

    ' return the status
    AecDtlApplication.Recipe.ReturnStatus = status

End Sub
Public Sub AecDtlLippedTileSection()

    Dim dblTileLen As Double
    Dim dblTileThick As Double
    Dim dblHeadLap As Double
    Dim dblLipThick As Double
    Dim dblLipOver As Double
    Dim dblFactor As Double
    Dim dblBatWid As Double
    Dim dblBatDep As Double
    Dim dblPnt(0 To 2) As Double
    Dim blkdef1 As AcadBlock
    Dim blkdef2 As AcadBlock
    Dim blkdef3 As AcadBlock
    Dim dblStep As Double
    Dim dblGap As Double
    Dim dblTileAng As Double
    Dim varP1 As Variant
    Dim varP2 As Variant
    Dim varP3 As Variant
    Dim varP4 As Variant
    Dim varP5 As Variant
    Dim varP6 As Variant
    Dim varP7 As Variant
    Dim varP8 As Variant
    Dim varP9 As Variant
    Dim line As AcadLine
    
    dblPnt(0) = 0#
    dblPnt(1) = 0#
    dblPnt(2) = 0#
    
    Set blkdef1 = ThisDrawing.Blocks.Add(dblPnt, "*U")
    Set blkdef2 = ThisDrawing.Blocks.Add(dblPnt, "*U")
    Set blkdef3 = ThisDrawing.Blocks.Add(dblPnt, "*U")
    
    dblTileLen = AecDtlApplication.Palette.GetPropertyValueDoubleUnitDep("TileLen")
    dblTileThick = AecDtlApplication.Palette.GetPropertyValueDoubleUnitDep("TileThick")
    dblHeadLap = AecDtlApplication.Palette.GetPropertyValueDoubleUnitDep("HeadLap")
    dblLipThick = AecDtlApplication.Palette.GetPropertyValueDoubleUnitDep("LipThick")
    dblLipOver = AecDtlApplication.Palette.GetPropertyValueDoubleUnitDep("LipOver")
    dblFactor = AecDtlApplication.Recipe.GetDataValueDoubleUnitDep("Values", "Factor")
    dblBatWid = AecDtlApplication.Recipe.GetDataValueDoubleUnitDep("Values", "BatWid")
    dblBatDep = AecDtlApplication.Recipe.GetDataValueDoubleUnitDep("Values", "BatDep")

    dblStep = Sqr((dblTileThick * dblTileThick) + ((dblTileLen - dblHeadLap) * (dblTileLen - dblHeadLap)))
    dblTileAng = Atn(dblTileThick / (dblTileLen - dblHeadLap))
    dblGap = dblLipOver * Tan(dblTileAng)
        
    varP1 = dblPnt
    varP1(0) = dblStep * 0.5
    varP1(1) = dblBatDep
    blkdef2.InsertBlock varP1, CreateTimberSection(dblBatWid, dblBatDep, "batten").Name, 1#, 1#, 1#, 0#
    blkdef3.InsertBlock varP1, CreateTimberSection(dblBatWid, dblBatDep, "batten").Name, 1#, 1#, 1#, 0#
    
    varP2 = varP1
    varP2(0) = varP2(0) + dblBatWid
    varP3 = CDLPolar(varP2, -dblTileAng, dblGap)
    varP2 = CDLPolar(varP3, Pi - dblTileAng, dblTileLen - dblLipThick)
    
    CDLIntLineLine varP2, varP3, Array(0#, 0#, 0#), Array(0#, 1#, 0#), varP4
    
    varP5 = varP4
    varP6 = varP2
    varP5(0) = varP5(0) + Abs(varP2(0))
    varP6(0) = varP6(0) + Abs(varP2(0))
    Set line = blkdef1.AddLine(varP5, varP6)
    AecDtlApplication.Recipe.SetEntityProperties "tile", line
    varP7 = CDLPolar(varP6, Pi * 0.5 - dblTileAng, dblTileThick)
    Set line = blkdef1.AddLine(varP6, varP7)
    AecDtlApplication.Recipe.SetEntityProperties "tile", line
    varP8 = CDLPolar(varP7, -dblTileAng, dblTileLen)
    CDLIntLineLine varP7, varP8, Array(varP5(0), 0#, 0#), Array(varP5(0), 1#, 0#), varP9
    Set line = blkdef1.AddLine(varP7, varP9)
    AecDtlApplication.Recipe.SetEntityProperties "tile", line
    
    Set line = blkdef2.AddLine(varP4, varP3)
    AecDtlApplication.Recipe.SetEntityProperties "tile", line
    varP5 = CDLPolar(varP3, -Pi * 0.5 - dblTileAng, dblLipThick)
    Set line = blkdef2.AddLine(varP3, varP5)
    AecDtlApplication.Recipe.SetEntityProperties "tile", line
    varP6 = CDLPolar(varP5, -dblTileAng, dblLipOver)
    Set line = blkdef2.AddLine(varP5, varP6)
    AecDtlApplication.Recipe.SetEntityProperties "tile", line
    varP7 = CDLPolar(varP6, Pi * 0.5 - dblTileAng, dblLipThick + dblTileThick)
    Set line = blkdef2.AddLine(varP6, varP7)
    AecDtlApplication.Recipe.SetEntityProperties "tile", line
    varP8 = CDLPolar(varP7, Pi - dblTileAng, dblTileLen)
    CDLIntLineLine varP7, varP8, Array(0#, 0#, 0#), Array(0#, 1#, 0#), varP9
    Set line = blkdef2.AddLine(varP7, varP9)
    AecDtlApplication.Recipe.SetEntityProperties "tile", line
    
    Set line = blkdef3.AddLine(varP4, varP3)
    AecDtlApplication.Recipe.SetEntityProperties "tile", line
    Set line = blkdef3.AddLine(varP3, varP5)
    AecDtlApplication.Recipe.SetEntityProperties "tile", line
    Set line = blkdef3.AddLine(varP5, varP6)
    AecDtlApplication.Recipe.SetEntityProperties "tile", line
    Set line = blkdef3.AddLine(varP6, varP7)
    AecDtlApplication.Recipe.SetEntityProperties "tile", line
    Set line = blkdef3.AddLine(varP7, varP9)
    AecDtlApplication.Recipe.SetEntityProperties "tile", line
    
    varP8 = CDLPolar(varP7, -dblTileAng, dblTileLen)
    CDLIntLineLine varP7, varP8, Array(dblStep, 0#, 0#), Array(dblStep, 1#, 0#), varP6
    Set line = blkdef2.AddLine(varP7, varP6)
    AecDtlApplication.Recipe.SetEntityProperties "tile", line
    varP8 = CDLPolar(varP7, Pi - dblTileAng, dblHeadLap)
    varP6 = CDLPolar(varP8, Pi * 0.5 - dblTileAng, dblTileThick)
    Set line = blkdef2.AddLine(varP8, varP6)
    AecDtlApplication.Recipe.SetEntityProperties "tile", line
    varP8 = CDLPolar(varP6, -dblTileAng, dblHeadLap)
    CDLIntLineLine varP6, varP8, Array(dblStep, 0#, 0#), Array(dblStep, 1#, 0#), varP7
    Set line = blkdef2.AddLine(varP7, varP6)
    AecDtlApplication.Recipe.SetEntityProperties "tile", line
    
    
    ' start the jig
    Dim status As AecDtlPromptStatus
    status = AecDtlApplication.jig.BookendsBlock(blkdef1, blkdef3, blkdef2)

    ' return the status
    AecDtlApplication.Recipe.ReturnStatus = status

End Sub
Public Sub AecDtlRaftFdnSection()

    Dim dblPnt(0 To 2) As Double
    Dim blkdef As AcadBlock
    Dim dblWallThick As Double
    Dim blnEarthHatch As Boolean
    Dim blnConcreteHatch As Boolean
    Dim dblDTOF As Double
    Dim dblDOT As Double
    Dim dblFOOTWID As Double
    Dim dblSLABTHICK As Double
    Dim dblSANDTHICK As Double
    Dim dblHARDTHICK As Double
    Dim dblFLOORLEN As Double
    Dim varP1 As Variant
    Dim varP2 As Variant
    Dim varP3 As Variant
    Dim varP4 As Variant
    Dim dblFactor As Double
    Dim line As AcadLine
    Dim pline As AcadPolyline
    Dim objHatch As AcadHatch
    Dim outerLoop(0 To 0) As AcadEntity
    Dim dblChamfer As Double
    
    dblPnt(0) = 0#
    dblPnt(1) = 0#
    dblPnt(2) = 0#
    
    Set blkdef = ThisDrawing.Blocks.Add(dblPnt, "*U")
    
    dblWallThick = AecDtlApplication.Palette.GetPropertyValueDoubleUnitDep("WallThick")
    dblDTOF = AecDtlApplication.Palette.GetPropertyValueDoubleUnitDep("DTOF")
    dblDOT = AecDtlApplication.Palette.GetPropertyValueDoubleUnitDep("DOT")
    dblFOOTWID = AecDtlApplication.Palette.GetPropertyValueDoubleUnitDep("FOOTWID")
    dblSLABTHICK = AecDtlApplication.Palette.GetPropertyValueDoubleUnitDep("SLABTHICK")
    dblSANDTHICK = AecDtlApplication.Palette.GetPropertyValueDoubleUnitDep("SANDTHICK")
    dblHARDTHICK = AecDtlApplication.Palette.GetPropertyValueDoubleUnitDep("HARDTHICK")
    dblFLOORLEN = AecDtlApplication.Palette.GetPropertyValueDoubleUnitDep("FLOORLEN")
    blnEarthHatch = AecDtlApplication.Palette.GetPropertyValueBool("doEarthHatch")
    blnConcreteHatch = AecDtlApplication.Palette.GetPropertyValueBool("doConcreteHatch")
    dblFactor = AecDtlApplication.Recipe.GetDataValueDoubleUnitDep("Values", "Factor")
    dblChamfer = AecDtlApplication.Recipe.GetDataValueDoubleUnitDep("Values", "Chamfer")
       
    varP1 = dblPnt
    varP1(1) = dblDTOF
    varP2 = varP1
    varP2(0) = -((dblFOOTWID - dblWallThick) * 0.5 + 450# * dblFactor)
    Set line = blkdef.AddLine(varP1, varP2)
    AecDtlApplication.Recipe.SetEntityProperties "soil", line
    
    If blnEarthHatch Then

        ReDim dblPnts(0 To 32) As Double
        
        dblPnts(0) = 0#: dblPnts(1) = 0#: dblPnts(2) = 0#
        dblPnts(3) = -5# * dblFactor: dblPnts(4) = 0#: dblPnts(5) = 0#
        dblPnts(6) = -5# * dblFactor: dblPnts(7) = -(dblDOT - dblDTOF): dblPnts(8) = 0#
        dblPnts(9) = dblFOOTWID - 5# * dblFactor: dblPnts(10) = -(dblDOT - dblDTOF): dblPnts(11) = 0#
        dblPnts(12) = (dblFOOTWID - 5# * dblFactor) * 0.5: dblPnts(13) = -(dblDOT - dblDTOF) - 150# * dblFactor: dblPnts(14) = 0#
        dblPnts(15) = -5# * dblFactor: dblPnts(16) = -(dblDOT - dblDTOF) - 75# * dblFactor: dblPnts(17) = 0#
        dblPnts(18) = -5# * dblFactor - 75# * dblFactor: dblPnts(19) = -(dblDOT - dblDTOF): dblPnts(20) = 0#
        dblPnts(21) = -5# * dblFactor - 75# * dblFactor: dblPnts(22) = 0#: dblPnts(23) = 0#
        dblPnts(24) = -150 * dblFactor: dblPnts(25) = dblDTOF: dblPnts(26) = 0#
        dblPnts(27) = 0#: dblPnts(28) = dblDTOF: dblPnts(29) = 0#
        dblPnts(30) = 0#: dblPnts(31) = 0#: dblPnts(32) = 0#
        
        Set pline = blkdef.AddPolyline(dblPnts)
        
        Set objHatch = blkdef.AddHatch(0, "ANSI31", True)
        AecDtlApplication.Recipe.SetHatchProperties "earth", objHatch
        AecDtlApplication.Recipe.SetEntityProperties "earth", objHatch
        Set outerLoop(0) = pline
        objHatch.AppendOuterLoop outerLoop
        objHatch.Evaluate
        
        pline.Delete
        
    End If

    ReDim dblPnts(0 To 26) As Double
    
    dblPnts(0) = dblWallThick + 5# * dblFactor + dblFLOORLEN: dblPnts(1) = dblDTOF: dblPnts(2) = 0#
    dblPnts(3) = dblWallThick + 5# * dblFactor: dblPnts(4) = dblDTOF: dblPnts(5) = 0#
    dblPnts(6) = dblWallThick + 5# * dblFactor: dblPnts(7) = 0#: dblPnts(8) = 0#
    dblPnts(9) = -5# * dblFactor: dblPnts(10) = 0#: dblPnts(11) = 0#
    dblPnts(12) = -5# * dblFactor: dblPnts(13) = -(dblDOT - dblDTOF): dblPnts(14) = 0#
    dblPnts(15) = dblFOOTWID - 5# * dblFactor: dblPnts(16) = -(dblDOT - dblDTOF): dblPnts(17) = 0#
    dblPnts(18) = dblFOOTWID - 5# * dblFactor: dblPnts(19) = dblDTOF - dblSLABTHICK - dblChamfer: dblPnts(20) = 0#
    dblPnts(21) = dblFOOTWID - 5# * dblFactor + dblChamfer: dblPnts(22) = dblDTOF - dblSLABTHICK: dblPnts(23) = 0#
    dblPnts(24) = dblWallThick + 5# * dblFactor + dblFLOORLEN: dblPnts(25) = dblDTOF - dblSLABTHICK: dblPnts(26) = 0#
    
    Set pline = blkdef.AddPolyline(dblPnts)
    AecDtlApplication.Recipe.SetEntityProperties "boundary", pline
    
    If blnConcreteHatch Then
    
        pline.Closed = True
        
        Set objHatch = blkdef.AddHatch(0, "ANSI31", True)
        AecDtlApplication.Recipe.SetHatchProperties "block", objHatch
        AecDtlApplication.Recipe.SetEntityProperties "concrete", objHatch
        Set outerLoop(0) = pline
        objHatch.AppendOuterLoop outerLoop
        objHatch.Evaluate
        
        pline.Closed = False
        
    End If
    
    ReDim dblPnts(0 To 14) As Double
    
    dblPnts(0) = dblWallThick + 5# * dblFactor + dblFLOORLEN: dblPnts(1) = dblDTOF - dblSLABTHICK: dblPnts(2) = 0#
    dblPnts(3) = dblWallThick + 5# * dblFactor + dblFLOORLEN: dblPnts(4) = dblDTOF - dblSLABTHICK - dblSANDTHICK: dblPnts(5) = 0#
    dblPnts(6) = dblFOOTWID - 5# * dblFactor + dblChamfer - dblSANDTHICK: dblPnts(7) = dblDTOF - dblSLABTHICK - dblSANDTHICK: dblPnts(8) = 0#
    dblPnts(9) = dblFOOTWID - 5# * dblFactor + dblChamfer: dblPnts(10) = dblDTOF - dblSLABTHICK: dblPnts(11) = 0#
    dblPnts(12) = dblWallThick + 5# * dblFactor + dblFLOORLEN: dblPnts(13) = dblDTOF - dblSLABTHICK: dblPnts(14) = 0#
    
    Set pline = blkdef.AddPolyline(dblPnts)
    
    Set objHatch = blkdef.AddHatch(0, "ANSI31", True)
    AecDtlApplication.Recipe.SetHatchProperties "sandfill", objHatch
    AecDtlApplication.Recipe.SetEntityProperties "sand", objHatch
    Set outerLoop(0) = pline
    objHatch.AppendOuterLoop outerLoop
    objHatch.Evaluate
    
    pline.Delete
    
    varP1 = dblPnt
    varP2 = dblPnt
    varP3 = dblPnt
    varP1(0) = dblFOOTWID - 5# * dblFactor + dblChamfer - dblSANDTHICK: varP1(1) = dblDTOF - dblSLABTHICK - dblSANDTHICK
    varP2(0) = dblWallThick + 5# * dblFactor + dblFLOORLEN: varP2(1) = dblDTOF - dblSLABTHICK - dblSANDTHICK
    Set line = blkdef.AddLine(varP1, varP2)
    AecDtlApplication.Recipe.SetEntityProperties "sand", line
    
    varP1(1) = varP1(1) - dblHARDTHICK
    blkdef.InsertBlock varP1, CreateHardcore((dblWallThick + 5# * dblFactor + dblFLOORLEN) - (dblFOOTWID - 5# * dblFactor + dblChamfer - dblSANDTHICK), dblHARDTHICK, "hardcore", "", False, False).Name, 1#, 1#, 1#, -Pi * 0.5
    
    varP2(0) = dblFOOTWID - 5# * dblFactor: varP2(1) = dblDTOF - dblSLABTHICK - dblChamfer
    varP3(0) = dblFOOTWID - 5# * dblFactor + dblChamfer: varP3(1) = dblDTOF - dblSLABTHICK
    CDLPerp varP2, varP3, varP1, varP4
    Set line = blkdef.AddLine(varP1, varP4)
    AecDtlApplication.Recipe.SetEntityProperties "hardcore", line

    ' start the jig
    Dim status As AecDtlPromptStatus
    status = AecDtlApplication.jig.StampBlock(blkdef)

    ' return the status
    AecDtlApplication.Recipe.ReturnStatus = status

End Sub
Public Sub AecDtlStripFtngSection()

    Dim dblPnt(0 To 2) As Double
    Dim blkdef As AcadBlock
    Dim dblWallThick As Double
    Dim blnEarthHatch As Boolean
    Dim blnConcreteHatch As Boolean
    Dim dblDTOF As Double
    Dim dblDOT As Double
    Dim dblFOOTWID As Double
    Dim varP1 As Variant
    Dim varP2 As Variant
    Dim dblFactor As Double
    Dim line As AcadLine
    Dim pline As AcadPolyline
    Dim objHatch As AcadHatch
    Dim outerLoop(0 To 0) As AcadEntity
    
    dblPnt(0) = 0#
    dblPnt(1) = 0#
    dblPnt(2) = 0#
    
    Set blkdef = ThisDrawing.Blocks.Add(dblPnt, "*U")
    
    dblWallThick = AecDtlApplication.Palette.GetPropertyValueDoubleUnitDep("WallThick")
    dblDTOF = AecDtlApplication.Palette.GetPropertyValueDoubleUnitDep("DTOF")
    dblDOT = AecDtlApplication.Palette.GetPropertyValueDoubleUnitDep("DOT")
    dblFOOTWID = AecDtlApplication.Palette.GetPropertyValueDoubleUnitDep("FOOTWID")
    blnEarthHatch = AecDtlApplication.Palette.GetPropertyValueBool("doEarthHatch")
    blnConcreteHatch = AecDtlApplication.Palette.GetPropertyValueBool("doConcreteHatch")
    dblFactor = AecDtlApplication.Recipe.GetDataValueDoubleUnitDep("Values", "Factor")
       
    varP1 = dblPnt
    varP1(0) = -(dblFOOTWID - dblWallThick) * 0.5
    varP1(1) = -(dblDOT - dblDTOF)
    blkdef.InsertBlock varP1, CreateBlock(dblFOOTWID, dblDOT - dblDTOF, blnConcreteHatch, "boundary", "block").Name, 1#, 1#, 1#, 0#
    varP1 = dblPnt
    varP1(1) = dblDTOF
    varP2 = varP1
    varP2(0) = -((dblFOOTWID - dblWallThick) * 0.5 + 450# * dblFactor)
    Set line = blkdef.AddLine(varP1, varP2)
    AecDtlApplication.Recipe.SetEntityProperties "soil", line
    
    If blnEarthHatch Then

        ReDim dblPnts(0 To 44) As Double
        
        dblPnts(0) = 0#: dblPnts(1) = 0#: dblPnts(2) = 0#
        dblPnts(3) = -(dblFOOTWID - dblWallThick) * 0.5: dblPnts(4) = 0#: dblPnts(5) = 0#
        dblPnts(6) = -(dblFOOTWID - dblWallThick) * 0.5: dblPnts(7) = -(dblDOT - dblDTOF): dblPnts(8) = 0#
        dblPnts(9) = dblFOOTWID - (dblFOOTWID - dblWallThick) * 0.5: dblPnts(10) = -(dblDOT - dblDTOF): dblPnts(11) = 0#
        dblPnts(12) = dblFOOTWID - (dblFOOTWID - dblWallThick) * 0.5: dblPnts(13) = 0#: dblPnts(14) = 0#
        dblPnts(15) = dblFOOTWID - (dblFOOTWID - dblWallThick) * 0.5 + 150 * dblFactor: dblPnts(16) = 0#: dblPnts(17) = 0#
        dblPnts(18) = dblFOOTWID - (dblFOOTWID - dblWallThick) * 0.5 + 75 * dblFactor: dblPnts(19) = -(dblDOT - dblDTOF): dblPnts(20) = 0#
        dblPnts(21) = dblFOOTWID - (dblFOOTWID - dblWallThick) * 0.5: dblPnts(22) = -(dblDOT - dblDTOF) - 75# * dblFactor: dblPnts(23) = 0#
        dblPnts(24) = dblWallThick * 0.5: dblPnts(25) = -(dblDOT - dblDTOF) - 150# * dblFactor: dblPnts(26) = 0#
        dblPnts(27) = -(dblFOOTWID - dblWallThick) * 0.5: dblPnts(28) = -(dblDOT - dblDTOF) - 75# * dblFactor: dblPnts(29) = 0#
        dblPnts(30) = -(dblFOOTWID - dblWallThick) * 0.5 - 75# * dblFactor: dblPnts(31) = -(dblDOT - dblDTOF): dblPnts(32) = 0#
        dblPnts(33) = -(dblFOOTWID - dblWallThick) * 0.5 - 75# * dblFactor: dblPnts(34) = 0#: dblPnts(35) = 0#
        dblPnts(36) = -150 * dblFactor: dblPnts(37) = dblDTOF: dblPnts(38) = 0#
        dblPnts(39) = 0#: dblPnts(40) = dblDTOF: dblPnts(41) = 0#
        dblPnts(42) = 0#: dblPnts(43) = 0#: dblPnts(44) = 0#
        
        Set pline = blkdef.AddPolyline(dblPnts)
        
        Set objHatch = blkdef.AddHatch(0, "ANSI31", True)
        AecDtlApplication.Recipe.SetHatchProperties "earth", objHatch
        AecDtlApplication.Recipe.SetEntityProperties "earth", objHatch
        Set outerLoop(0) = pline
        objHatch.AppendOuterLoop outerLoop
        objHatch.Evaluate
        
        pline.Delete
        
    End If

    ' start the jig
    Dim status As AecDtlPromptStatus
    status = AecDtlApplication.jig.StampBlock(blkdef)

    ' return the status
    AecDtlApplication.Recipe.ReturnStatus = status

End Sub
Public Sub AecDtlStoneTimberSection()

    Dim dblPnt(0 To 2) As Double
    Dim blkdef1 As AcadBlock
    Dim blkdef2 As AcadBlock
    Dim blkdef3 As AcadBlock
    Dim blnHatchBlock As Boolean
    Dim dblJoint As Double
    Dim dblHeight As Double
    Dim dblBlockThick As Double
    Dim dblStudThick As Double
    Dim dblCavityThick As Double
    Dim blnInsulation As Boolean
    Dim varP1 As Variant
    Dim intNoStuds As Integer
    Dim dblStudSize As Double
    Dim blnPlywood As Boolean
    Dim blnDry As Boolean
    Dim dblPlywoodThick As Double
    Dim dblDryThick As Double
    
    dblPnt(0) = 0#
    dblPnt(1) = 0#
    dblPnt(2) = 0#
    
    Set blkdef1 = ThisDrawing.Blocks.Add(dblPnt, "*U")
    Set blkdef2 = ThisDrawing.Blocks.Add(dblPnt, "*U")
    Set blkdef3 = ThisDrawing.Blocks.Add(dblPnt, "*U")
    
    dblJoint = AecDtlApplication.Database.GetFieldValueDoubleUnitDep("JOINT")
    dblHeight = AecDtlApplication.Database.GetFieldValueDoubleUnitDep("HEIGHT")
    dblBlockThick = AecDtlApplication.Database.GetFieldValueDoubleUnitDep("STONE_THICK")
    dblStudThick = AecDtlApplication.Database.GetFieldValueDoubleUnitDep("STUD_THICK")
    
    blnHatchBlock = AecDtlApplication.Palette.GetPropertyValueBool("doStoneHatch")
    blnInsulation = AecDtlApplication.Palette.GetPropertyValueBool("showInsulation")
    dblCavityThick = AecDtlApplication.Palette.GetPropertyValueDoubleUnitDep("CavityThick")
    dblStudSize = AecDtlApplication.Palette.GetPropertyValueDoubleUnitDep("StudSize")
    intNoStuds = AecDtlApplication.Palette.GetPropertyValueStr("NoStudsTop")
    blnPlywood = AecDtlApplication.Palette.GetPropertyValueBool("showPlywood")
    blnDry = AecDtlApplication.Palette.GetPropertyValueBool("showDry")
    dblPlywoodThick = AecDtlApplication.Palette.GetPropertyValueDoubleUnitDep("PlywoodThick")
    dblDryThick = AecDtlApplication.Palette.GetPropertyValueDoubleUnitDep("DryThick")

    ' Create bottom Block
    varP1 = dblPnt
    blkdef1.InsertBlock varP1, CreateMortar(dblBlockThick, dblJoint).Name, 1#, 1#, 1#, 0#
    varP1(1) = dblJoint
    blkdef1.InsertBlock varP1, CreateBlock(dblBlockThick, dblHeight, blnHatchBlock, "block", "blockinfill").Name, 1#, 1#, 1#, 0#

    varP1 = dblPnt
    varP1(0) = varP1(0) + dblBlockThick + dblCavityThick
    varP1(1) = dblStudSize
    blkdef1.InsertBlock varP1, CreateTimberSection(dblStudThick, dblStudSize, "stud").Name, 1#, 1#, 1#, 0#
    varP1 = dblPnt
    varP1(0) = varP1(0) + dblBlockThick + dblCavityThick
    varP1(1) = dblStudSize
    blkdef1.InsertBlock varP1, CreateBlock(dblStudThick, dblHeight + dblJoint - dblStudSize, False, "stud", "", True, False, True, False).Name, 1#, 1#, 1#, 0#
    varP1 = dblPnt
    varP1(0) = varP1(0) + dblBlockThick + dblCavityThick - dblPlywoodThick
    If blnPlywood Then
        blkdef1.InsertBlock varP1, CreateBlock(dblPlywoodThick, dblHeight + dblJoint, False, "stud", "", True, False, False, True).Name, 1#, 1#, 1#, 0#
    End If
    varP1(0) = varP1(0) + dblPlywoodThick + dblStudThick
    If blnDry Then
        blkdef1.InsertBlock varP1, CreateBlock(dblDryThick, dblHeight + dblJoint, False, "stud", "", False, False, True, True).Name, 1#, 1#, 1#, 0#
    End If
    varP1 = dblPnt
    varP1(0) = varP1(0) + dblBlockThick + dblCavityThick + dblStudThick
    varP1(1) = dblStudSize
    If blnInsulation Then
        blkdef1.InsertBlock varP1, CreateInsulation(dblHeight + dblJoint - dblStudSize, dblStudThick, "insulation", "", False, False).Name, 1#, 1#, 1#, 0#
    End If

    ' Intermediate Block
    varP1 = dblPnt
    blkdef2.InsertBlock varP1, CreateMortar(dblBlockThick, dblJoint).Name, 1#, 1#, 1#, 0#
    varP1(1) = dblJoint
    blkdef2.InsertBlock varP1, CreateBlock(dblBlockThick, dblHeight, blnHatchBlock, "block", "blockinfill").Name, 1#, 1#, 1#, 0#
    
    varP1 = dblPnt
    varP1(0) = varP1(0) + dblBlockThick + dblCavityThick
    blkdef2.InsertBlock varP1, CreateBlock(dblStudThick, dblHeight + dblJoint, False, "stud", "", True, False, True, False).Name, 1#, 1#, 1#, 0#
    varP1(0) = varP1(0) - dblPlywoodThick
    If blnPlywood Then
        blkdef2.InsertBlock varP1, CreateBlock(0#, dblHeight + dblJoint, False, "stud", "", True, False, False, False).Name, 1#, 1#, 1#, 0#
    End If
    varP1(0) = varP1(0) + dblPlywoodThick + dblStudThick
    If blnDry Then
        blkdef2.InsertBlock varP1, CreateBlock(dblDryThick, dblHeight + dblJoint, False, "stud", "", False, False, True, False).Name, 1#, 1#, 1#, 0#
    End If
    varP1 = dblPnt
    varP1(0) = varP1(0) + dblBlockThick + dblCavityThick + dblStudThick
    If blnInsulation Then
        blkdef2.InsertBlock varP1, CreateInsulation(dblHeight + dblJoint, dblStudThick, "insulation", "", False, False).Name, 1#, 1#, 1#, 0#
    End If
    
    ' Top Block
    varP1 = dblPnt
    blkdef3.InsertBlock varP1, CreateMortar(dblBlockThick, dblJoint).Name, 1#, 1#, 1#, 0#
    varP1(1) = dblJoint
    blkdef3.InsertBlock varP1, CreateBlock(dblBlockThick, dblHeight, blnHatchBlock, "block", "blockinfill").Name, 1#, 1#, 1#, 0#
    varP1 = dblPnt
    varP1(0) = varP1(0) + dblBlockThick + dblCavityThick
    varP1(1) = dblHeight + dblJoint
    blkdef3.InsertBlock varP1, CreateTimberSection(dblStudThick, dblStudSize, "stud").Name, 1#, 1#, 1#, 0#
    If intNoStuds > 1 Then
        varP1(1) = varP1(1) - dblStudSize
        blkdef3.InsertBlock varP1, CreateTimberSection(dblStudThick, dblStudSize, "stud").Name, 1#, 1#, 1#, 0#
    End If
    varP1 = dblPnt
    varP1(0) = varP1(0) + dblBlockThick + dblCavityThick
    blkdef3.InsertBlock varP1, CreateBlock(dblStudThick, dblHeight + dblJoint - dblStudSize * intNoStuds, False, "stud", "", True, False, True, False).Name, 1#, 1#, 1#, 0#
    varP1(0) = varP1(0) - dblPlywoodThick
    If blnPlywood Then
        blkdef3.InsertBlock varP1, CreateBlock(dblPlywoodThick, dblHeight + dblJoint, False, "stud", "", True, True, False, False).Name, 1#, 1#, 1#, 0#
    End If
    varP1(0) = varP1(0) + dblPlywoodThick + dblStudThick
    If blnDry Then
        blkdef3.InsertBlock varP1, CreateBlock(dblDryThick, dblHeight + dblJoint, False, "stud", "", False, True, True, False).Name, 1#, 1#, 1#, 0#
    End If
    varP1 = dblPnt
    varP1(0) = varP1(0) + dblBlockThick + dblCavityThick + dblStudThick
    If blnInsulation Then
        blkdef3.InsertBlock varP1, CreateInsulation(dblHeight + dblJoint - dblStudSize * intNoStuds, dblStudThick, "insulation", "", False, False).Name, 1#, 1#, 1#, 0#
    End If
    

    ' start the jig
    Dim status As AecDtlPromptStatus
    status = AecDtlApplication.jig.BookendsBlock(blkdef1, blkdef3, blkdef2)

    ' return the status
    AecDtlApplication.Recipe.ReturnStatus = status

End Sub
Public Sub AecDtlBlockTimberSection()

    Dim dblPnt(0 To 2) As Double
    Dim blkdef1 As AcadBlock
    Dim blkdef2 As AcadBlock
    Dim blkdef3 As AcadBlock
    Dim blnHatchBlock As Boolean
    Dim dblJoint As Double
    Dim dblHeight As Double
    Dim dblBlockThick As Double
    Dim dblStudThick As Double
    Dim dblCavityThick As Double
    Dim blnInsulation As Boolean
    Dim varP1 As Variant
    Dim intNoStuds As Integer
    Dim dblStudSize As Double
    Dim blnPlywood As Boolean
    Dim blnDry As Boolean
    Dim dblPlywoodThick As Double
    Dim dblDryThick As Double
    
    dblPnt(0) = 0#
    dblPnt(1) = 0#
    dblPnt(2) = 0#
    
    Set blkdef1 = ThisDrawing.Blocks.Add(dblPnt, "*U")
    Set blkdef2 = ThisDrawing.Blocks.Add(dblPnt, "*U")
    Set blkdef3 = ThisDrawing.Blocks.Add(dblPnt, "*U")
    
    dblJoint = AecDtlApplication.Database.GetFieldValueDoubleUnitDep("JOINT")
    dblHeight = AecDtlApplication.Database.GetFieldValueDoubleUnitDep("HEIGHT")
    dblBlockThick = AecDtlApplication.Database.GetFieldValueDoubleUnitDep("BLOCK_THICK")
    dblStudThick = AecDtlApplication.Database.GetFieldValueDoubleUnitDep("STUD_THICK")
    
    blnHatchBlock = AecDtlApplication.Palette.GetPropertyValueBool("doBlockHatch")
    blnInsulation = AecDtlApplication.Palette.GetPropertyValueBool("showInsulation")
    dblCavityThick = AecDtlApplication.Palette.GetPropertyValueDoubleUnitDep("CavityThick")
    dblStudSize = AecDtlApplication.Palette.GetPropertyValueDoubleUnitDep("StudSize")
    intNoStuds = AecDtlApplication.Palette.GetPropertyValueStr("NoStudsTop")
    blnPlywood = AecDtlApplication.Palette.GetPropertyValueBool("showPlywood")
    blnDry = AecDtlApplication.Palette.GetPropertyValueBool("showDry")
    dblPlywoodThick = AecDtlApplication.Palette.GetPropertyValueDoubleUnitDep("PlywoodThick")
    dblDryThick = AecDtlApplication.Palette.GetPropertyValueDoubleUnitDep("DryThick")

    ' Create bottom Block
    varP1 = dblPnt
    blkdef1.InsertBlock varP1, CreateMortar(dblBlockThick, dblJoint).Name, 1#, 1#, 1#, 0#
    varP1(1) = dblJoint
    blkdef1.InsertBlock varP1, CreateBlock(dblBlockThick, dblHeight, blnHatchBlock, "block", "blockinfill").Name, 1#, 1#, 1#, 0#

    varP1 = dblPnt
    varP1(0) = varP1(0) + dblBlockThick + dblCavityThick
    varP1(1) = dblStudSize
    blkdef1.InsertBlock varP1, CreateTimberSection(dblStudThick, dblStudSize, "stud").Name, 1#, 1#, 1#, 0#
    varP1 = dblPnt
    varP1(0) = varP1(0) + dblBlockThick + dblCavityThick
    varP1(1) = dblStudSize
    blkdef1.InsertBlock varP1, CreateBlock(dblStudThick, dblHeight + dblJoint - dblStudSize, False, "stud", "", True, False, True, False).Name, 1#, 1#, 1#, 0#
    varP1 = dblPnt
    varP1(0) = varP1(0) + dblBlockThick + dblCavityThick - dblPlywoodThick
    If blnPlywood Then
        blkdef1.InsertBlock varP1, CreateBlock(dblPlywoodThick, dblHeight + dblJoint, False, "stud", "", True, False, False, True).Name, 1#, 1#, 1#, 0#
    End If
    varP1(0) = varP1(0) + dblPlywoodThick + dblStudThick
    If blnDry Then
        blkdef1.InsertBlock varP1, CreateBlock(dblDryThick, dblHeight + dblJoint, False, "stud", "", False, False, True, True).Name, 1#, 1#, 1#, 0#
    End If
    varP1 = dblPnt
    varP1(0) = varP1(0) + dblBlockThick + dblCavityThick + dblStudThick
    varP1(1) = dblStudSize
    If blnInsulation Then
        blkdef1.InsertBlock varP1, CreateInsulation(dblHeight + dblJoint - dblStudSize, dblStudThick, "insulation", "", False, False).Name, 1#, 1#, 1#, 0#
    End If

    ' Intermediate Block
    varP1 = dblPnt
    blkdef2.InsertBlock varP1, CreateMortar(dblBlockThick, dblJoint).Name, 1#, 1#, 1#, 0#
    varP1(1) = dblJoint
    blkdef2.InsertBlock varP1, CreateBlock(dblBlockThick, dblHeight, blnHatchBlock, "block", "blockinfill").Name, 1#, 1#, 1#, 0#
    
    varP1 = dblPnt
    varP1(0) = varP1(0) + dblBlockThick + dblCavityThick
    blkdef2.InsertBlock varP1, CreateBlock(dblStudThick, dblHeight + dblJoint, False, "stud", "", True, False, True, False).Name, 1#, 1#, 1#, 0#
    varP1(0) = varP1(0) - dblPlywoodThick
    If blnPlywood Then
        blkdef2.InsertBlock varP1, CreateBlock(0#, dblHeight + dblJoint, False, "stud", "", True, False, False, False).Name, 1#, 1#, 1#, 0#
    End If
    varP1(0) = varP1(0) + dblPlywoodThick + dblStudThick
    If blnDry Then
        blkdef2.InsertBlock varP1, CreateBlock(dblDryThick, dblHeight + dblJoint, False, "stud", "", False, False, True, False).Name, 1#, 1#, 1#, 0#
    End If
    varP1 = dblPnt
    varP1(0) = varP1(0) + dblBlockThick + dblCavityThick + dblStudThick
    If blnInsulation Then
        blkdef2.InsertBlock varP1, CreateInsulation(dblHeight + dblJoint, dblStudThick, "insulation", "", False, False).Name, 1#, 1#, 1#, 0#
    End If
    
    ' Top Block
    varP1 = dblPnt
    blkdef3.InsertBlock varP1, CreateMortar(dblBlockThick, dblJoint).Name, 1#, 1#, 1#, 0#
    varP1(1) = dblJoint
    blkdef3.InsertBlock varP1, CreateBlock(dblBlockThick, dblHeight, blnHatchBlock, "block", "blockinfill").Name, 1#, 1#, 1#, 0#
    varP1 = dblPnt
    varP1(0) = varP1(0) + dblBlockThick + dblCavityThick
    varP1(1) = dblHeight + dblJoint
    blkdef3.InsertBlock varP1, CreateTimberSection(dblStudThick, dblStudSize, "stud").Name, 1#, 1#, 1#, 0#
    If intNoStuds > 1 Then
        varP1(1) = varP1(1) - dblStudSize
        blkdef3.InsertBlock varP1, CreateTimberSection(dblStudThick, dblStudSize, "stud").Name, 1#, 1#, 1#, 0#
    End If
    varP1 = dblPnt
    varP1(0) = varP1(0) + dblBlockThick + dblCavityThick
    blkdef3.InsertBlock varP1, CreateBlock(dblStudThick, dblHeight + dblJoint - dblStudSize * intNoStuds, False, "stud", "", True, False, True, False).Name, 1#, 1#, 1#, 0#
    varP1(0) = varP1(0) - dblPlywoodThick
    If blnPlywood Then
        blkdef3.InsertBlock varP1, CreateBlock(dblPlywoodThick, dblHeight + dblJoint, False, "stud", "", True, True, False, False).Name, 1#, 1#, 1#, 0#
    End If
    varP1(0) = varP1(0) + dblPlywoodThick + dblStudThick
    If blnDry Then
        blkdef3.InsertBlock varP1, CreateBlock(dblDryThick, dblHeight + dblJoint, False, "stud", "", False, True, True, False).Name, 1#, 1#, 1#, 0#
    End If
    varP1 = dblPnt
    varP1(0) = varP1(0) + dblBlockThick + dblCavityThick + dblStudThick
    If blnInsulation Then
        blkdef3.InsertBlock varP1, CreateInsulation(dblHeight + dblJoint - dblStudSize * intNoStuds, dblStudThick, "insulation", "", False, False).Name, 1#, 1#, 1#, 0#
    End If
    

    ' start the jig
    Dim status As AecDtlPromptStatus
    status = AecDtlApplication.jig.BookendsBlock(blkdef1, blkdef3, blkdef2)

    ' return the status
    AecDtlApplication.Recipe.ReturnStatus = status

End Sub
Public Sub AecDtlBrickTimberSection()

    Dim dblPnt(0 To 2) As Double
    Dim blkdef1 As AcadBlock
    Dim blkdef2 As AcadBlock
    Dim blkdef3 As AcadBlock
    Dim blnHatchBrick As Boolean
    Dim dblJoint As Double
    Dim dblHeight As Double
    Dim dblBrickThick As Double
    Dim dblStudThick As Double
    Dim dblCavityThick As Double
    Dim blnInsulation As Boolean
    Dim varP1 As Variant
    Dim intNoStuds As Integer
    Dim dblStudSize As Double
    Dim blnPlywood As Boolean
    Dim blnDry As Boolean
    Dim dblPlywoodThick As Double
    Dim dblDryThick As Double
    
    dblPnt(0) = 0#
    dblPnt(1) = 0#
    dblPnt(2) = 0#
    
    Set blkdef1 = ThisDrawing.Blocks.Add(dblPnt, "*U")
    Set blkdef2 = ThisDrawing.Blocks.Add(dblPnt, "*U")
    Set blkdef3 = ThisDrawing.Blocks.Add(dblPnt, "*U")
    
    dblJoint = AecDtlApplication.Database.GetFieldValueDoubleUnitDep("JOINT")
    dblHeight = AecDtlApplication.Database.GetFieldValueDoubleUnitDep("HEIGHT")
    dblBrickThick = AecDtlApplication.Database.GetFieldValueDoubleUnitDep("BRICK_THICK")
    dblStudThick = AecDtlApplication.Database.GetFieldValueDoubleUnitDep("STUD_THICK")
    
    blnHatchBrick = AecDtlApplication.Palette.GetPropertyValueBool("doBrickHatch")
    blnInsulation = AecDtlApplication.Palette.GetPropertyValueBool("showInsulation")
    dblCavityThick = AecDtlApplication.Palette.GetPropertyValueDoubleUnitDep("CavityThick")
    dblStudSize = AecDtlApplication.Palette.GetPropertyValueDoubleUnitDep("StudSize")
    intNoStuds = AecDtlApplication.Palette.GetPropertyValueStr("NoStudsTop")
    blnPlywood = AecDtlApplication.Palette.GetPropertyValueBool("showPlywood")
    blnDry = AecDtlApplication.Palette.GetPropertyValueBool("showDry")
    dblPlywoodThick = AecDtlApplication.Palette.GetPropertyValueDoubleUnitDep("PlywoodThick")
    dblDryThick = AecDtlApplication.Palette.GetPropertyValueDoubleUnitDep("DryThick")

    ' Create bottom Block
    varP1 = dblPnt
    blkdef1.InsertBlock varP1, CreateMortar(dblBrickThick, dblJoint).Name, 1#, 1#, 1#, 0#
    varP1(1) = dblJoint
    blkdef1.InsertBlock varP1, CreateBlock(dblBrickThick, dblHeight, blnHatchBrick, "block", "infill").Name, 1#, 1#, 1#, 0#

    varP1 = dblPnt
    varP1(0) = varP1(0) + dblBrickThick + dblCavityThick
    varP1(1) = dblStudSize
    blkdef1.InsertBlock varP1, CreateTimberSection(dblStudThick, dblStudSize, "stud").Name, 1#, 1#, 1#, 0#
    varP1 = dblPnt
    varP1(0) = varP1(0) + dblBrickThick + dblCavityThick
    varP1(1) = dblStudSize
    blkdef1.InsertBlock varP1, CreateBlock(dblStudThick, dblHeight + dblJoint - dblStudSize, False, "stud", "", True, False, True, False).Name, 1#, 1#, 1#, 0#
    varP1 = dblPnt
    varP1(0) = varP1(0) + dblBrickThick + dblCavityThick - dblPlywoodThick
    If blnPlywood Then
        blkdef1.InsertBlock varP1, CreateBlock(dblPlywoodThick, dblHeight + dblJoint, False, "stud", "", True, False, False, True).Name, 1#, 1#, 1#, 0#
    End If
    varP1(0) = varP1(0) + dblPlywoodThick + dblStudThick
    If blnDry Then
        blkdef1.InsertBlock varP1, CreateBlock(dblDryThick, dblHeight + dblJoint, False, "stud", "", False, False, True, True).Name, 1#, 1#, 1#, 0#
    End If
    varP1 = dblPnt
    varP1(0) = varP1(0) + dblBrickThick + dblCavityThick + dblStudThick
    varP1(1) = dblStudSize
    If blnInsulation Then
        blkdef1.InsertBlock varP1, CreateInsulation(dblHeight + dblJoint - dblStudSize, dblStudThick, "insulation", "", False, False).Name, 1#, 1#, 1#, 0#
    End If

    ' Intermediate Block
    varP1 = dblPnt
    blkdef2.InsertBlock varP1, CreateMortar(dblBrickThick, dblJoint).Name, 1#, 1#, 1#, 0#
    varP1(1) = dblJoint
    blkdef2.InsertBlock varP1, CreateBlock(dblBrickThick, dblHeight, blnHatchBrick, "block", "infill").Name, 1#, 1#, 1#, 0#
    
    varP1 = dblPnt
    varP1(0) = varP1(0) + dblBrickThick + dblCavityThick
    blkdef2.InsertBlock varP1, CreateBlock(dblStudThick, dblHeight + dblJoint, False, "stud", "", True, False, True, False).Name, 1#, 1#, 1#, 0#
    varP1(0) = varP1(0) - dblPlywoodThick
    If blnPlywood Then
        blkdef2.InsertBlock varP1, CreateBlock(0#, dblHeight + dblJoint, False, "stud", "", True, False, False, False).Name, 1#, 1#, 1#, 0#
    End If
    varP1(0) = varP1(0) + dblPlywoodThick + dblStudThick
    If blnDry Then
        blkdef2.InsertBlock varP1, CreateBlock(dblDryThick, dblHeight + dblJoint, False, "stud", "", False, False, True, False).Name, 1#, 1#, 1#, 0#
    End If
    varP1 = dblPnt
    varP1(0) = varP1(0) + dblBrickThick + dblCavityThick + dblStudThick
    If blnInsulation Then
        blkdef2.InsertBlock varP1, CreateInsulation(dblHeight + dblJoint, dblStudThick, "insulation", "", False, False).Name, 1#, 1#, 1#, 0#
    End If
    
    ' Top Block
    varP1 = dblPnt
    blkdef3.InsertBlock varP1, CreateMortar(dblBrickThick, dblJoint).Name, 1#, 1#, 1#, 0#
    varP1(1) = dblJoint
    blkdef3.InsertBlock varP1, CreateBlock(dblBrickThick, dblHeight, blnHatchBrick, "block", "infill").Name, 1#, 1#, 1#, 0#
    If intNoStuds > 1 Then
        varP1(1) = varP1(1) + dblHeight
        blkdef3.InsertBlock varP1, CreateMortar(dblBrickThick, dblJoint).Name, 1#, 1#, 1#, 0#
        varP1(1) = varP1(1) + dblJoint
        blkdef3.InsertBlock varP1, CreateBlock(dblBrickThick, dblHeight, blnHatchBrick, "block", "infill").Name, 1#, 1#, 1#, 0#
    End If
    varP1 = dblPnt
    varP1(0) = varP1(0) + dblBrickThick + dblCavityThick
    varP1(1) = (dblHeight + dblJoint) * intNoStuds
    blkdef3.InsertBlock varP1, CreateTimberSection(dblStudThick, dblStudSize, "stud").Name, 1#, 1#, 1#, 0#
    If intNoStuds > 1 Then
        varP1(1) = varP1(1) - dblStudSize
        blkdef3.InsertBlock varP1, CreateTimberSection(dblStudThick, dblStudSize, "stud").Name, 1#, 1#, 1#, 0#
    End If
    varP1 = dblPnt
    varP1(0) = varP1(0) + dblBrickThick + dblCavityThick
    blkdef3.InsertBlock varP1, CreateBlock(dblStudThick, (dblHeight + dblJoint - dblStudSize) * intNoStuds, False, "stud", "", True, False, True, False).Name, 1#, 1#, 1#, 0#
    varP1(0) = varP1(0) - dblPlywoodThick
    If blnPlywood Then
        blkdef3.InsertBlock varP1, CreateBlock(dblPlywoodThick, (dblHeight + dblJoint) * intNoStuds, False, "stud", "", True, True, False, False).Name, 1#, 1#, 1#, 0#
    End If
    varP1(0) = varP1(0) + dblPlywoodThick + dblStudThick
    If blnDry Then
        blkdef3.InsertBlock varP1, CreateBlock(dblDryThick, (dblHeight + dblJoint) * intNoStuds, False, "stud", "", False, True, True, False).Name, 1#, 1#, 1#, 0#
    End If
    varP1 = dblPnt
    varP1(0) = varP1(0) + dblBrickThick + dblCavityThick + dblStudThick
    If blnInsulation Then
        blkdef3.InsertBlock varP1, CreateInsulation((dblHeight + dblJoint - dblStudSize) * intNoStuds, dblStudThick, "insulation", "", False, False).Name, 1#, 1#, 1#, 0#
    End If
    

    ' start the jig
    Dim status As AecDtlPromptStatus
    status = AecDtlApplication.jig.BookendsBlock(blkdef1, blkdef3, blkdef2)

    ' return the status
    AecDtlApplication.Recipe.ReturnStatus = status

End Sub
Public Sub AecDtlTrussUK()

    Dim dblPnt(0 To 2) As Double
    Dim blkdef As AcadBlock
    Dim dblSpan As Double
    Dim dblPitch As Double
    Dim dblRafterThick As Double
    Dim dblTieThick As Double
    Dim dblOverhang As Double
    Dim line1 As AcadLine
    Dim line2 As AcadLine
    Dim line3 As AcadLine
    Dim line4 As AcadLine
    Dim line5 As AcadLine
    Dim line6 As AcadLine
    Dim line7 As AcadLine
    Dim line8 As AcadLine
    Dim line9 As AcadLine
    Dim line10 As AcadLine
    Dim line11 As AcadLine
    Dim line12 As AcadLine
    Dim line13 As AcadLine
    Dim line14 As AcadLine
    Dim line15 As AcadLine
    Dim line16 As AcadLine
    Dim line17 As AcadLine
    Dim line18 As AcadLine
    Dim line19 As AcadLine
    Dim varP1 As Variant
    Dim varP2 As Variant
    Dim varP3 As Variant
    Dim varP4 As Variant
    Dim strType As String
    Dim dblFlrJstThick As Double
    Dim dblStrutSize As Double
    Dim dblStrutOffset As Double
    Dim dblClgTieHgt As Double
    Dim dblClgTieSize As Double
    
    dblPnt(0) = 0#
    dblPnt(1) = 0#
    dblPnt(2) = 0#
    
    Set blkdef = ThisDrawing.Blocks.Add(dblPnt, "*U")

    strType = AecDtlApplication.Recipe.GetDataValueStr("rafter", "Type")

    dblSpan = AecDtlApplication.Palette.GetPropertyValueDoubleUnitDep("Span")
    dblPitch = AecDtlApplication.Palette.GetPropertyValueDouble("Pitch")
    dblRafterThick = AecDtlApplication.Palette.GetPropertyValueDoubleUnitDep("RafterThick")
    dblOverhang = AecDtlApplication.Palette.GetPropertyValueDoubleUnitDep("Overhang")
    If strType = "E" Then
        dblFlrJstThick = AecDtlApplication.Palette.GetPropertyValueDoubleUnitDep("FlrJstThick")
        dblStrutSize = AecDtlApplication.Palette.GetPropertyValueDoubleUnitDep("StrutSize")
        dblStrutOffset = AecDtlApplication.Palette.GetPropertyValueDoubleUnitDep("StrutOffset")
        dblClgTieHgt = AecDtlApplication.Palette.GetPropertyValueDoubleUnitDep("ClgTieHght")
        dblClgTieSize = AecDtlApplication.Palette.GetPropertyValueDoubleUnitDep("ClgTieSize")
    Else
        dblTieThick = AecDtlApplication.Palette.GetPropertyValueDoubleUnitDep("TieThick")
    End If

    ' Draw Rafters
    varP1 = dblPnt
    varP2 = dblPnt
    varP2(0) = dblSpan
    Set line1 = blkdef.AddLine(varP1, varP2)
    AecDtlApplication.Recipe.SetEntityProperties "rafter", line1
    
    If strType <> "E" Then
        varP1(1) = varP1(1) + dblRafterThick
        varP2(1) = varP2(1) + dblRafterThick
    Else
        varP1(1) = varP1(1) + dblFlrJstThick
        varP2(1) = varP2(1) + dblFlrJstThick
    End If
    Set line2 = blkdef.AddLine(varP1, varP2)
    AecDtlApplication.Recipe.SetEntityProperties "rafter", line2
    
    varP1 = dblPnt
    varP2 = CDLPolar(varP1, dblPitch * DegToRad, 10#)
    Set line3 = blkdef.AddLine(varP1, varP2)
    AecDtlApplication.Recipe.SetEntityProperties "rafter", line3
    
    varP1 = line1.EndPoint
    varP2 = CDLPolar(varP1, (180# - dblPitch) * DegToRad, 10#)
    Set line4 = blkdef.AddLine(varP1, varP2)
    AecDtlApplication.Recipe.SetEntityProperties "rafter", line4
    
    varP1 = line3.IntersectWith(line4, acExtendBoth)
    line3.EndPoint = varP1
    line4.EndPoint = varP1
    
    varP1 = line3.IntersectWith(line2, acExtendBoth)
    varP2 = line4.IntersectWith(line2, acExtendBoth)
    line2.StartPoint = varP1
    line2.EndPoint = varP2
    
    varP1 = CDLPolar(line3.StartPoint, (dblPitch + 90#) * DegToRad, dblRafterThick)
    varP2 = CDLPolar(line3.EndPoint, (dblPitch + 90#) * DegToRad, dblRafterThick)
    Set line5 = blkdef.AddLine(varP1, varP2)
    AecDtlApplication.Recipe.SetEntityProperties "rafter", line5

    varP1 = CDLPolar(line4.StartPoint, (180# - dblPitch - 90#) * DegToRad, dblRafterThick)
    varP2 = CDLPolar(line4.EndPoint, (180# - dblPitch - 90#) * DegToRad, dblRafterThick)
    Set line6 = blkdef.AddLine(varP1, varP2)
    AecDtlApplication.Recipe.SetEntityProperties "rafter", line6

    varP1 = line5.IntersectWith(line6, acExtendBoth)
    line5.EndPoint = varP1
    line6.EndPoint = varP1
    
    Set line7 = blkdef.AddLine(line4.EndPoint, line6.EndPoint)
    AecDtlApplication.Recipe.SetEntityProperties "rafter", line7
    
    varP1 = dblPnt
    varP1(0) = -dblOverhang
    varP2 = varP1
    varP2(1) = 10#
    Set line8 = blkdef.AddLine(varP1, varP2)
    AecDtlApplication.Recipe.SetEntityProperties "rafter", line8
    
    varP1 = line3.IntersectWith(line8, acExtendBoth)
    varP2 = line5.IntersectWith(line8, acExtendBoth)
    line8.StartPoint = varP1
    line8.EndPoint = varP2
    line5.StartPoint = varP2
    line3.StartPoint = varP1

    varP1(0) = dblOverhang + dblSpan
    varP2(0) = dblOverhang + dblSpan
    Set line9 = blkdef.AddLine(varP1, varP2)
    AecDtlApplication.Recipe.SetEntityProperties "rafter", line9
    
    line4.StartPoint = line9.StartPoint
    line6.StartPoint = line9.EndPoint
    
    ' Draw tie
    Select Case UCase(strType)
        Case "A"
        
            varP1 = CDLPolar(line2.StartPoint, 0#, line2.Length * 0.3333333)
            CDLPerp line3.StartPoint, line3.EndPoint, varP1, varP2
            varP3 = CDLPolar(varP1, CDLAngle(varP1, varP2) + Pi * 0.5, dblTieThick * 0.5)
            varP4 = CDLPolar(varP2, CDLAngle(varP1, varP2) + Pi * 0.5, dblTieThick * 0.5)
            Set line12 = blkdef.AddLine(varP3, varP4)
            AecDtlApplication.Recipe.SetEntityProperties "rafter", line12
            varP3 = CDLPolar(varP1, CDLAngle(varP1, varP2) - Pi * 0.5, dblTieThick * 0.5)
            varP4 = CDLPolar(varP2, CDLAngle(varP1, varP2) - Pi * 0.5, dblTieThick * 0.5)
            Set line13 = blkdef.AddLine(varP3, varP4)
            AecDtlApplication.Recipe.SetEntityProperties "rafter", line13
            
            varP1 = CDLPolar(line2.StartPoint, 0#, line2.Length * 0.3333333)
            varP2 = line3.EndPoint
            varP3 = CDLPolar(varP1, CDLAngle(varP1, varP2) + Pi * 0.5, dblTieThick * 0.5)
            varP4 = CDLPolar(varP2, CDLAngle(varP1, varP2) + Pi * 0.5, dblTieThick * 0.5)
            Set line14 = blkdef.AddLine(varP3, varP4)
            AecDtlApplication.Recipe.SetEntityProperties "rafter", line14
            varP3 = CDLPolar(varP1, CDLAngle(varP1, varP2) - Pi * 0.5, dblTieThick * 0.5)
            varP4 = CDLPolar(varP2, CDLAngle(varP1, varP2) - Pi * 0.5, dblTieThick * 0.5)
            Set line15 = blkdef.AddLine(varP3, varP4)
            AecDtlApplication.Recipe.SetEntityProperties "rafter", line15
            
            varP1 = line12.IntersectWith(line2, acExtendBoth)
            line12.StartPoint = varP1
            varP1 = line13.IntersectWith(line14, acExtendBoth)
            line13.StartPoint = varP1
            line14.StartPoint = varP1
            varP1 = line15.IntersectWith(line2, acExtendBoth)
            line15.StartPoint = varP1
            varP1 = line14.IntersectWith(line3, acExtendBoth)
            line14.EndPoint = varP1
            varP1 = line15.IntersectWith(line7, acExtendBoth)
            line15.EndPoint = varP1
            
            AecDtlApplication.Recipe.SetEntityProperties "rafter", blkdef.AddLine(line15.EndPoint, line3.EndPoint)
            
            varP1 = CDLPolar(line2.StartPoint, 0#, line2.Length * 0.3333333)
            CDLPerp line3.StartPoint, line3.EndPoint, varP1, varP2
            varP3 = CDLPolar(varP1, line12.Angle, dblTieThick * 3#)
            AecDtlApplication.Recipe.SetEntityProperties "cline", blkdef.AddLine(varP1, varP3)
            varP3 = CDLPolar(varP1, line14.Angle, dblTieThick * 3#)
            AecDtlApplication.Recipe.SetEntityProperties "cline", blkdef.AddLine(varP1, varP3)
            varP3 = CDLPolar(varP2, CDLAngle(varP2, varP1), dblTieThick * 3#)
            AecDtlApplication.Recipe.SetEntityProperties "cline", blkdef.AddLine(varP2, varP3)
            varP2 = line3.EndPoint
            varP3 = CDLPolar(varP2, CDLAngle(varP2, varP1), dblTieThick * 3#)
            AecDtlApplication.Recipe.SetEntityProperties "cline", blkdef.AddLine(varP2, varP3)
            
            varP1 = CDLPolar(line2.EndPoint, Pi, line2.Length * 0.3333333)
            CDLPerp line4.StartPoint, line4.EndPoint, varP1, varP2
            varP3 = CDLPolar(varP1, CDLAngle(varP1, varP2) + Pi * 0.5, dblTieThick * 0.5)
            varP4 = CDLPolar(varP2, CDLAngle(varP1, varP2) + Pi * 0.5, dblTieThick * 0.5)
            Set line12 = blkdef.AddLine(varP3, varP4)
            AecDtlApplication.Recipe.SetEntityProperties "rafter", line12
            varP3 = CDLPolar(varP1, CDLAngle(varP1, varP2) - Pi * 0.5, dblTieThick * 0.5)
            varP4 = CDLPolar(varP2, CDLAngle(varP1, varP2) - Pi * 0.5, dblTieThick * 0.5)
            Set line13 = blkdef.AddLine(varP3, varP4)
            AecDtlApplication.Recipe.SetEntityProperties "rafter", line13
            
            varP1 = CDLPolar(line2.EndPoint, Pi, line2.Length * 0.3333333)
            varP2 = line3.EndPoint
            varP3 = CDLPolar(varP1, CDLAngle(varP1, varP2) + Pi * 0.5, dblTieThick * 0.5)
            varP4 = CDLPolar(varP2, CDLAngle(varP1, varP2) + Pi * 0.5, dblTieThick * 0.5)
            Set line14 = blkdef.AddLine(varP3, varP4)
            AecDtlApplication.Recipe.SetEntityProperties "rafter", line14
            varP3 = CDLPolar(varP1, CDLAngle(varP1, varP2) - Pi * 0.5, dblTieThick * 0.5)
            varP4 = CDLPolar(varP2, CDLAngle(varP1, varP2) - Pi * 0.5, dblTieThick * 0.5)
            Set line15 = blkdef.AddLine(varP3, varP4)
            AecDtlApplication.Recipe.SetEntityProperties "rafter", line15

            varP1 = line13.IntersectWith(line2, acExtendBoth)
            line13.StartPoint = varP1
            varP1 = line12.IntersectWith(line15, acExtendBoth)
            line12.StartPoint = varP1
            line15.StartPoint = varP1
            varP1 = line14.IntersectWith(line2, acExtendBoth)
            line14.StartPoint = varP1
            varP1 = line15.IntersectWith(line4, acExtendBoth)
            line15.EndPoint = varP1
            varP1 = line14.IntersectWith(line7, acExtendBoth)
            line14.EndPoint = varP1

            varP1 = CDLPolar(line2.EndPoint, Pi, line2.Length * 0.3333333)
            CDLPerp line4.StartPoint, line4.EndPoint, varP1, varP2
            varP3 = CDLPolar(varP1, line12.Angle, dblTieThick * 3#)
            AecDtlApplication.Recipe.SetEntityProperties "cline", blkdef.AddLine(varP1, varP3)
            varP3 = CDLPolar(varP1, line14.Angle, dblTieThick * 3#)
            AecDtlApplication.Recipe.SetEntityProperties "cline", blkdef.AddLine(varP1, varP3)
            varP3 = CDLPolar(varP2, CDLAngle(varP2, varP1), dblTieThick * 3#)
            AecDtlApplication.Recipe.SetEntityProperties "cline", blkdef.AddLine(varP2, varP3)
            varP2 = line3.EndPoint
            varP3 = CDLPolar(varP2, CDLAngle(varP2, varP1), dblTieThick * 3#)
            AecDtlApplication.Recipe.SetEntityProperties "cline", blkdef.AddLine(varP2, varP3)
        
        Case "B"
        
            varP1(0) = dblSpan * 0.5 - dblTieThick * 0.5
            varP1(1) = dblRafterThick
            varP2 = varP1
            varP2(1) = varP2(1) + 10#
            Set line10 = blkdef.AddLine(varP1, varP2)
            AecDtlApplication.Recipe.SetEntityProperties "rafter", line10
            
            varP2 = line10.IntersectWith(line3, acExtendBoth)
            line10.EndPoint = varP2
            
            varP1(0) = varP1(0) + dblTieThick
            varP2(0) = varP2(0) + dblTieThick
            Set line11 = blkdef.AddLine(varP1, varP2)
            AecDtlApplication.Recipe.SetEntityProperties "rafter", line11
            
            varP1(0) = dblSpan * 0.5
            varP1(1) = dblRafterThick
            varP2 = varP1
            varP2(1) = varP2(1) + dblTieThick * 3#
            AecDtlApplication.Recipe.SetEntityProperties "cline", blkdef.AddLine(varP1, varP2)
            varP1 = line3.EndPoint
            varP2 = varP1
            varP2(1) = varP2(1) - dblTieThick * 3#
            AecDtlApplication.Recipe.SetEntityProperties "cline", blkdef.AddLine(varP1, varP2)
            
            varP1 = line11.StartPoint
            varP2 = CDLPolar(line2.EndPoint, line4.Angle, CDLDist(line2.EndPoint, line4.EndPoint) * 0.5)
            varP3 = CDLPolar(varP1, CDLAngle(varP1, varP2) + Pi * 0.5, dblTieThick * 0.5)
            varP4 = CDLPolar(varP2, CDLAngle(varP1, varP2) + Pi * 0.5, dblTieThick * 0.5)
            Set line16 = blkdef.AddLine(varP3, varP4)
            AecDtlApplication.Recipe.SetEntityProperties "rafter", line16
            varP3 = CDLPolar(varP1, CDLAngle(varP1, varP2) - Pi * 0.5, dblTieThick * 0.5)
            varP4 = CDLPolar(varP2, CDLAngle(varP1, varP2) - Pi * 0.5, dblTieThick * 0.5)
            Set line17 = blkdef.AddLine(varP3, varP4)
            AecDtlApplication.Recipe.SetEntityProperties "rafter", line17

            varP1 = line16.IntersectWith(line11, acExtendBoth)
            line16.StartPoint = varP1
            varP1 = line16.IntersectWith(line4, acExtendBoth)
            line16.EndPoint = varP1
            varP1 = line17.IntersectWith(line2, acExtendBoth)
            line17.StartPoint = varP1
            varP1 = line17.IntersectWith(line4, acExtendBoth)
            line17.EndPoint = varP1

            varP1 = line11.StartPoint
            varP2 = CDLPolar(line11.StartPoint, line16.Angle, dblTieThick * 3#)
            AecDtlApplication.Recipe.SetEntityProperties "cline", blkdef.AddLine(varP1, varP2)
            varP1 = CDLPolar(line16.EndPoint, CDLAngle(line16.EndPoint, line17.EndPoint), CDLDist(line16.EndPoint, line17.EndPoint) * 0.5)
            varP2 = CDLPolar(varP1, line16.Angle + Pi, dblTieThick * 3#)
            AecDtlApplication.Recipe.SetEntityProperties "cline", blkdef.AddLine(varP1, varP2)

            varP1 = line10.StartPoint
            varP2 = CDLPolar(line2.StartPoint, line3.Angle, CDLDist(line2.EndPoint, line3.EndPoint) * 0.5)
            varP3 = CDLPolar(varP1, CDLAngle(varP1, varP2) + Pi * 0.5, dblTieThick * 0.5)
            varP4 = CDLPolar(varP2, CDLAngle(varP1, varP2) + Pi * 0.5, dblTieThick * 0.5)
            Set line18 = blkdef.AddLine(varP3, varP4)
            AecDtlApplication.Recipe.SetEntityProperties "rafter", line18
            varP3 = CDLPolar(varP1, CDLAngle(varP1, varP2) - Pi * 0.5, dblTieThick * 0.5)
            varP4 = CDLPolar(varP2, CDLAngle(varP1, varP2) - Pi * 0.5, dblTieThick * 0.5)
            Set line19 = blkdef.AddLine(varP3, varP4)
            AecDtlApplication.Recipe.SetEntityProperties "rafter", line19

            varP1 = line18.IntersectWith(line2, acExtendBoth)
            line18.StartPoint = varP1
            varP1 = line18.IntersectWith(line3, acExtendBoth)
            line18.EndPoint = varP1
            varP1 = line19.IntersectWith(line10, acExtendBoth)
            line19.StartPoint = varP1
            varP1 = line19.IntersectWith(line3, acExtendBoth)
            line19.EndPoint = varP1

            varP1 = line10.StartPoint
            varP2 = CDLPolar(line10.StartPoint, CDLAngle(line18.StartPoint, line18.EndPoint), dblTieThick * 3#)
            AecDtlApplication.Recipe.SetEntityProperties "cline", blkdef.AddLine(varP1, varP2)
            varP1 = CDLPolar(line18.EndPoint, CDLAngle(line18.EndPoint, line19.EndPoint), CDLDist(line18.EndPoint, line19.EndPoint) * 0.5)
            varP2 = CDLPolar(varP1, CDLAngle(line18.EndPoint, line18.StartPoint), dblTieThick * 3#)
            AecDtlApplication.Recipe.SetEntityProperties "cline", blkdef.AddLine(varP1, varP2)
            
        Case "C"
        
            varP1(0) = dblSpan * 0.5 - dblTieThick * 0.5
            varP1(1) = dblRafterThick
            varP2 = varP1
            varP2(1) = varP2(1) + 10#
            Set line10 = blkdef.AddLine(varP1, varP2)
            AecDtlApplication.Recipe.SetEntityProperties "rafter", line10
            
            varP2 = line10.IntersectWith(line3, acExtendBoth)
            line10.EndPoint = varP2
            
            varP1(0) = varP1(0) + dblTieThick
            varP2(0) = varP2(0) + dblTieThick
            Set line11 = blkdef.AddLine(varP1, varP2)
            AecDtlApplication.Recipe.SetEntityProperties "rafter", line11
            
            varP1(0) = dblSpan * 0.5
            varP1(1) = dblRafterThick
            varP2 = varP1
            varP2(1) = varP2(1) + dblTieThick * 3#
            AecDtlApplication.Recipe.SetEntityProperties "cline", blkdef.AddLine(varP1, varP2)
            varP1 = line3.EndPoint
            varP2 = varP1
            varP2(1) = varP2(1) - dblTieThick * 3#
            AecDtlApplication.Recipe.SetEntityProperties "cline", blkdef.AddLine(varP1, varP2)
            
            varP1 = CDLPolar(line2.EndPoint, Pi, CDLDist(line2.EndPoint, line2.StartPoint) * 0.25)
            varP1(0) = varP1(0) - dblTieThick * 0.5
            varP2 = varP1
            varP2(1) = varP2(1) + 10#
            Set line12 = blkdef.AddLine(varP1, varP2)
            AecDtlApplication.Recipe.SetEntityProperties "rafter", line12
            
            varP2 = line12.IntersectWith(line4, acExtendBoth)
            line12.EndPoint = varP2
            
            varP1(0) = varP1(0) + dblTieThick
            varP2(0) = varP2(0) + dblTieThick
            Set line13 = blkdef.AddLine(varP1, varP2)
            AecDtlApplication.Recipe.SetEntityProperties "rafter", line13
        
            varP2 = line13.IntersectWith(line4, acExtendBoth)
            line13.EndPoint = varP2
            
            varP1 = CDLPolar(line12.StartPoint, 0#, CDLDist(line12.StartPoint, line13.StartPoint) * 0.5)
            varP2 = varP1
            varP2(1) = varP2(1) + dblTieThick * 3#
            AecDtlApplication.Recipe.SetEntityProperties "cline", blkdef.AddLine(varP1, varP2)
            varP1 = CDLPolar(line12.EndPoint, CDLAngle(line12.EndPoint, line13.EndPoint), CDLDist(line12.EndPoint, line13.EndPoint) * 0.5)
            varP2 = varP1
            varP2(1) = varP2(1) - dblTieThick * 3#
            AecDtlApplication.Recipe.SetEntityProperties "cline", blkdef.AddLine(varP1, varP2)
            
            varP1 = CDLPolar(line2.StartPoint, 0#, CDLDist(line2.EndPoint, line2.StartPoint) * 0.25)
            varP1(0) = varP1(0) - dblTieThick * 0.5
            varP2 = varP1
            varP2(1) = varP2(1) + 10#
            Set line14 = blkdef.AddLine(varP1, varP2)
            AecDtlApplication.Recipe.SetEntityProperties "rafter", line14
            
            varP2 = line14.IntersectWith(line3, acExtendBoth)
            line14.EndPoint = varP2
            
            varP1(0) = varP1(0) + dblTieThick
            varP2(0) = varP2(0) + dblTieThick
            Set line15 = blkdef.AddLine(varP1, varP2)
            AecDtlApplication.Recipe.SetEntityProperties "rafter", line15
        
            varP2 = line15.IntersectWith(line3, acExtendBoth)
            line15.EndPoint = varP2
            
            varP1 = CDLPolar(line14.StartPoint, 0#, CDLDist(line14.StartPoint, line15.StartPoint) * 0.5)
            varP2 = varP1
            varP2(1) = varP2(1) + dblTieThick * 3#
            AecDtlApplication.Recipe.SetEntityProperties "cline", blkdef.AddLine(varP1, varP2)
            varP1 = CDLPolar(line14.EndPoint, CDLAngle(line14.EndPoint, line15.EndPoint), CDLDist(line14.EndPoint, line15.EndPoint) * 0.5)
            varP2 = varP1
            varP2(1) = varP2(1) - dblTieThick * 3#
            AecDtlApplication.Recipe.SetEntityProperties "cline", blkdef.AddLine(varP1, varP2)
            
        Case "D"
        
            varP1(0) = dblSpan * 0.5 - dblTieThick * 0.5
            varP1(1) = dblRafterThick
            varP2 = varP1
            varP2(1) = varP2(1) + 10#
            Set line10 = blkdef.AddLine(varP1, varP2)
            AecDtlApplication.Recipe.SetEntityProperties "rafter", line10
            
            varP2 = line10.IntersectWith(line3, acExtendBoth)
            line10.EndPoint = varP2
            
            varP1(0) = varP1(0) + dblTieThick
            varP2(0) = varP2(0) + dblTieThick
            Set line11 = blkdef.AddLine(varP1, varP2)
            AecDtlApplication.Recipe.SetEntityProperties "rafter", line11
            
            varP1(0) = dblSpan * 0.5
            varP1(1) = dblRafterThick
            varP2 = varP1
            varP2(1) = varP2(1) + dblTieThick * 3#
            AecDtlApplication.Recipe.SetEntityProperties "cline", blkdef.AddLine(varP1, varP2)
            varP1 = line3.EndPoint
            varP2 = varP1
            varP2(1) = varP2(1) - dblTieThick * 3#
            AecDtlApplication.Recipe.SetEntityProperties "cline", blkdef.AddLine(varP1, varP2)
            
            varP1 = CDLPolar(line2.EndPoint, Pi, CDLDist(line2.EndPoint, line2.StartPoint) * 0.25)
            varP1(0) = varP1(0) - dblTieThick * 0.5
            varP2 = varP1
            varP2(1) = varP2(1) + 10#
            Set line12 = blkdef.AddLine(varP1, varP2)
            AecDtlApplication.Recipe.SetEntityProperties "rafter", line12
            
            varP2 = line12.IntersectWith(line4, acExtendBoth)
            line12.EndPoint = varP2
            
            varP1(0) = varP1(0) + dblTieThick
            varP2(0) = varP2(0) + dblTieThick
            Set line13 = blkdef.AddLine(varP1, varP2)
            AecDtlApplication.Recipe.SetEntityProperties "rafter", line13
        
            varP2 = line13.IntersectWith(line4, acExtendBoth)
            line13.EndPoint = varP2
            
            varP1 = CDLPolar(line12.StartPoint, 0#, CDLDist(line12.StartPoint, line13.StartPoint) * 0.5)
            varP2 = varP1
            varP2(1) = varP2(1) + dblTieThick * 3#
            AecDtlApplication.Recipe.SetEntityProperties "cline", blkdef.AddLine(varP1, varP2)
            varP1 = CDLPolar(line12.EndPoint, CDLAngle(line12.EndPoint, line13.EndPoint), CDLDist(line12.EndPoint, line13.EndPoint) * 0.5)
            varP2 = varP1
            varP2(1) = varP2(1) - dblTieThick * 3#
            AecDtlApplication.Recipe.SetEntityProperties "cline", blkdef.AddLine(varP1, varP2)
            
            varP1 = CDLPolar(line2.StartPoint, 0#, CDLDist(line2.EndPoint, line2.StartPoint) * 0.25)
            varP1(0) = varP1(0) - dblTieThick * 0.5
            varP2 = varP1
            varP2(1) = varP2(1) + 10#
            Set line14 = blkdef.AddLine(varP1, varP2)
            AecDtlApplication.Recipe.SetEntityProperties "rafter", line14
            
            varP2 = line14.IntersectWith(line3, acExtendBoth)
            line14.EndPoint = varP2
            
            varP1(0) = varP1(0) + dblTieThick
            varP2(0) = varP2(0) + dblTieThick
            Set line15 = blkdef.AddLine(varP1, varP2)
            AecDtlApplication.Recipe.SetEntityProperties "rafter", line15
        
            varP2 = line15.IntersectWith(line3, acExtendBoth)
            line15.EndPoint = varP2
            
            varP1 = CDLPolar(line14.StartPoint, 0#, CDLDist(line14.StartPoint, line15.StartPoint) * 0.5)
            varP2 = varP1
            varP2(1) = varP2(1) + dblTieThick * 3#
            AecDtlApplication.Recipe.SetEntityProperties "cline", blkdef.AddLine(varP1, varP2)
            varP1 = CDLPolar(line14.EndPoint, CDLAngle(line14.EndPoint, line15.EndPoint), CDLDist(line14.EndPoint, line15.EndPoint) * 0.5)
            varP2 = varP1
            varP2(1) = varP2(1) - dblTieThick * 3#
            AecDtlApplication.Recipe.SetEntityProperties "cline", blkdef.AddLine(varP1, varP2)
            
            varP1 = line10.StartPoint
            varP2 = line15.EndPoint
            varP3 = CDLPolar(varP1, CDLAngle(varP1, varP2) + Pi * 0.5, dblTieThick * 0.5)
            varP4 = CDLPolar(varP2, CDLAngle(varP1, varP2) + Pi * 0.5, dblTieThick * 0.5)
            Set line16 = blkdef.AddLine(varP3, varP4)
            AecDtlApplication.Recipe.SetEntityProperties "rafter", line16
            varP3 = CDLPolar(varP1, CDLAngle(varP1, varP2) - Pi * 0.5, dblTieThick * 0.5)
            varP4 = CDLPolar(varP2, CDLAngle(varP1, varP2) - Pi * 0.5, dblTieThick * 0.5)
            Set line17 = blkdef.AddLine(varP3, varP4)
            AecDtlApplication.Recipe.SetEntityProperties "rafter", line17
            
            varP1 = line16.IntersectWith(line2, acExtendBoth)
            line16.StartPoint = varP1
            varP1 = line16.IntersectWith(line15, acExtendBoth)
            line16.EndPoint = varP1
            varP1 = line17.IntersectWith(line10, acExtendBoth)
            line17.StartPoint = varP1
            varP1 = line17.IntersectWith(line3, acExtendBoth)
            line17.EndPoint = varP1
            
            varP1 = line10.StartPoint
            varP2 = CDLPolar(line10.StartPoint, CDLAngle(line16.StartPoint, line16.EndPoint), dblTieThick * 3#)
            AecDtlApplication.Recipe.SetEntityProperties "cline", blkdef.AddLine(varP1, varP2)
            varP1 = line15.EndPoint
            varP2 = CDLPolar(line15.EndPoint, CDLAngle(line16.EndPoint, line16.StartPoint), dblTieThick * 3#)
            AecDtlApplication.Recipe.SetEntityProperties "cline", blkdef.AddLine(varP1, varP2)
            
            varP1 = line11.StartPoint
            varP2 = line12.EndPoint
            varP3 = CDLPolar(varP1, CDLAngle(varP1, varP2) + Pi * 0.5, dblTieThick * 0.5)
            varP4 = CDLPolar(varP2, CDLAngle(varP1, varP2) + Pi * 0.5, dblTieThick * 0.5)
            Set line18 = blkdef.AddLine(varP3, varP4)
            AecDtlApplication.Recipe.SetEntityProperties "rafter", line18
            varP3 = CDLPolar(varP1, CDLAngle(varP1, varP2) - Pi * 0.5, dblTieThick * 0.5)
            varP4 = CDLPolar(varP2, CDLAngle(varP1, varP2) - Pi * 0.5, dblTieThick * 0.5)
            Set line19 = blkdef.AddLine(varP3, varP4)
            AecDtlApplication.Recipe.SetEntityProperties "rafter", line19
            
            varP1 = line18.IntersectWith(line11, acExtendBoth)
            line18.StartPoint = varP1
            varP1 = line18.IntersectWith(line4, acExtendBoth)
            line18.EndPoint = varP1
            varP1 = line19.IntersectWith(line2, acExtendBoth)
            line19.StartPoint = varP1
            varP1 = line19.IntersectWith(line12, acExtendBoth)
            line19.EndPoint = varP1

            varP1 = line11.StartPoint
            varP2 = CDLPolar(line11.StartPoint, CDLAngle(line18.StartPoint, line18.EndPoint), dblTieThick * 3#)
            AecDtlApplication.Recipe.SetEntityProperties "cline", blkdef.AddLine(varP1, varP2)
            varP1 = line12.EndPoint
            varP2 = CDLPolar(line12.EndPoint, CDLAngle(line18.EndPoint, line18.StartPoint), dblTieThick * 3#)
            AecDtlApplication.Recipe.SetEntityProperties "cline", blkdef.AddLine(varP1, varP2)
            
        Case "E"
        
            varP1 = CDLPolar(line2.EndPoint, Pi, dblStrutOffset)
            varP2 = varP1
            varP2(1) = varP2(1) + 10#
            Set line12 = blkdef.AddLine(varP1, varP2)
            AecDtlApplication.Recipe.SetEntityProperties "rafter", line12

            varP2 = line12.IntersectWith(line4, acExtendBoth)
            line12.EndPoint = varP2

            varP1(0) = varP1(0) + dblStrutSize
            varP2(0) = varP2(0) + dblStrutSize
            Set line13 = blkdef.AddLine(varP1, varP2)
            AecDtlApplication.Recipe.SetEntityProperties "rafter", line13

            varP2 = line13.IntersectWith(line4, acExtendBoth)
            line13.EndPoint = varP2

            varP1 = CDLPolar(line12.StartPoint, 0#, CDLDist(line12.StartPoint, line13.StartPoint) * 0.5)
            varP2 = varP1
            varP2(1) = varP2(1) + dblStrutSize * 3#
            AecDtlApplication.Recipe.SetEntityProperties "cline", blkdef.AddLine(varP1, varP2)
            varP1 = CDLPolar(line12.EndPoint, CDLAngle(line12.EndPoint, line13.EndPoint), CDLDist(line12.EndPoint, line13.EndPoint) * 0.5)
            varP2 = varP1
            varP2(1) = varP2(1) - dblStrutSize * 3#
            AecDtlApplication.Recipe.SetEntityProperties "cline", blkdef.AddLine(varP1, varP2)

            varP1 = CDLPolar(line2.StartPoint, 0#, dblStrutOffset)
            varP2 = varP1
            varP2(1) = varP2(1) + 10#
            Set line14 = blkdef.AddLine(varP1, varP2)
            AecDtlApplication.Recipe.SetEntityProperties "rafter", line14

            varP2 = line14.IntersectWith(line3, acExtendBoth)
            line14.EndPoint = varP2

            varP1(0) = varP1(0) + dblStrutSize
            varP2(0) = varP2(0) + dblStrutSize
            Set line15 = blkdef.AddLine(varP1, varP2)
            AecDtlApplication.Recipe.SetEntityProperties "rafter", line15

            varP2 = line15.IntersectWith(line3, acExtendBoth)
            line15.EndPoint = varP2

            varP1 = CDLPolar(line14.StartPoint, 0#, CDLDist(line14.StartPoint, line15.StartPoint) * 0.5)
            varP2 = varP1
            varP2(1) = varP2(1) + dblStrutSize * 3#
            AecDtlApplication.Recipe.SetEntityProperties "cline", blkdef.AddLine(varP1, varP2)
            varP1 = CDLPolar(line14.EndPoint, CDLAngle(line14.EndPoint, line15.EndPoint), CDLDist(line14.EndPoint, line15.EndPoint) * 0.5)
            varP2 = varP1
            varP2(1) = varP2(1) - dblStrutSize * 3#
            AecDtlApplication.Recipe.SetEntityProperties "cline", blkdef.AddLine(varP1, varP2)
            
            varP1 = line2.StartPoint
            varP1(1) = varP1(1) + dblClgTieHgt
            varP2 = line2.EndPoint
            varP2(1) = varP2(1) + dblClgTieHgt
            Set line16 = blkdef.AddLine(varP1, varP2)
            AecDtlApplication.Recipe.SetEntityProperties "rafter", line16

            varP1 = line16.IntersectWith(line3, acExtendBoth)
            line16.StartPoint = varP1
            varP2 = line16.IntersectWith(line4, acExtendBoth)
            line16.EndPoint = varP2
        
            varP1 = line2.StartPoint
            varP1(1) = varP1(1) + dblClgTieHgt + dblClgTieSize
            varP2 = line2.EndPoint
            varP2(1) = varP2(1) + dblClgTieHgt + dblClgTieSize
            Set line17 = blkdef.AddLine(varP1, varP2)
            AecDtlApplication.Recipe.SetEntityProperties "rafter", line17

            varP1 = line17.IntersectWith(line3, acExtendBoth)
            line17.StartPoint = varP1
            varP2 = line17.IntersectWith(line4, acExtendBoth)
            line17.EndPoint = varP2
        
            varP1 = CDLPolar(line16.StartPoint, line3.Angle, CDLDist(line16.StartPoint, line17.StartPoint) * 0.5)
            varP2 = varP1
            varP2(0) = varP2(0) + dblStrutSize * 3#
            AecDtlApplication.Recipe.SetEntityProperties "cline", blkdef.AddLine(varP1, varP2)
            varP1 = CDLPolar(line16.EndPoint, line4.Angle, CDLDist(line16.EndPoint, line17.EndPoint) * 0.5)
            varP2 = varP1
            varP2(0) = varP2(0) - dblStrutSize * 3#
            AecDtlApplication.Recipe.SetEntityProperties "cline", blkdef.AddLine(varP1, varP2)
        
        Case "F"
        
            varP1 = CDLPolar(line2.StartPoint, 0#, line2.Length * 0.3333333)
            varP2 = CDLPolar(line2.StartPoint, CDLAngle(line2.StartPoint, line3.EndPoint), CDLDist(line2.StartPoint, line3.EndPoint) * 0.3333333)
            varP3 = CDLPolar(varP1, CDLAngle(varP1, varP2) + Pi * 0.5, dblTieThick * 0.5)
            varP4 = CDLPolar(varP2, CDLAngle(varP1, varP2) + Pi * 0.5, dblTieThick * 0.5)
            Set line12 = blkdef.AddLine(varP3, varP4)
            AecDtlApplication.Recipe.SetEntityProperties "rafter", line12
            varP3 = CDLPolar(varP1, CDLAngle(varP1, varP2) - Pi * 0.5, dblTieThick * 0.5)
            varP4 = CDLPolar(varP2, CDLAngle(varP1, varP2) - Pi * 0.5, dblTieThick * 0.5)
            Set line13 = blkdef.AddLine(varP3, varP4)
            AecDtlApplication.Recipe.SetEntityProperties "rafter", line13
            
            varP1 = CDLPolar(line2.StartPoint, 0#, line2.Length * 0.3333333)
            varP2 = varP1
            varP2(1) = varP2(1) + dblSpan
            varP3 = CDLPolar(varP1, CDLAngle(varP1, varP2) + Pi * 0.5, dblTieThick * 0.5)
            varP4 = CDLPolar(varP2, CDLAngle(varP1, varP2) + Pi * 0.5, dblTieThick * 0.5)
            Set line14 = blkdef.AddLine(varP3, varP4)
            AecDtlApplication.Recipe.SetEntityProperties "rafter", line14
            varP3 = CDLPolar(varP1, CDLAngle(varP1, varP2) - Pi * 0.5, dblTieThick * 0.5)
            varP4 = CDLPolar(varP2, CDLAngle(varP1, varP2) - Pi * 0.5, dblTieThick * 0.5)
            Set line15 = blkdef.AddLine(varP3, varP4)
            AecDtlApplication.Recipe.SetEntityProperties "rafter", line15
            
            varP1 = CDLPolar(line2.StartPoint, 0#, line2.Length * 0.3333333)
            varP2 = line3.EndPoint
            varP3 = CDLPolar(varP1, CDLAngle(varP1, varP2) + Pi * 0.5, dblTieThick * 0.5)
            varP4 = CDLPolar(varP2, CDLAngle(varP1, varP2) + Pi * 0.5, dblTieThick * 0.5)
            Set line16 = blkdef.AddLine(varP3, varP4)
            AecDtlApplication.Recipe.SetEntityProperties "rafter", line16
            varP3 = CDLPolar(varP1, CDLAngle(varP1, varP2) - Pi * 0.5, dblTieThick * 0.5)
            varP4 = CDLPolar(varP2, CDLAngle(varP1, varP2) - Pi * 0.5, dblTieThick * 0.5)
            Set line17 = blkdef.AddLine(varP3, varP4)
            AecDtlApplication.Recipe.SetEntityProperties "rafter", line17
            
            varP1 = line12.IntersectWith(line2, acExtendBoth)
            line12.StartPoint = varP1
            varP1 = line13.IntersectWith(line14, acExtendBoth)
            line13.StartPoint = varP1
            varP1 = line16.IntersectWith(line15, acExtendBoth)
            line16.StartPoint = varP1
            varP1 = line17.IntersectWith(line2, acExtendBoth)
            line17.StartPoint = varP1
            varP1 = line12.IntersectWith(line3, acExtendBoth)
            line12.EndPoint = varP1
            varP1 = line13.IntersectWith(line3, acExtendBoth)
            line13.EndPoint = varP1
            varP1 = line14.IntersectWith(line3, acExtendBoth)
            line14.EndPoint = varP1
            varP1 = line15.IntersectWith(line3, acExtendBoth)
            line15.EndPoint = varP1
            varP1 = line16.IntersectWith(line3, acExtendBoth)
            line16.EndPoint = varP1
            varP1 = line17.IntersectWith(line7, acExtendBoth)
            line17.EndPoint = varP1

            AecDtlApplication.Recipe.SetEntityProperties "rafter", blkdef.AddLine(line17.EndPoint, line3.EndPoint)

            varP1 = CDLPolar(line2.StartPoint, 0#, line2.Length * 0.3333333)
            varP2 = CDLPolar(line2.StartPoint, CDLAngle(line2.StartPoint, line3.EndPoint), CDLDist(line2.StartPoint, line3.EndPoint) * 0.3333333)
            varP3 = CDLPolar(varP1, line12.Angle, dblTieThick * 3#)
            AecDtlApplication.Recipe.SetEntityProperties "cline", blkdef.AddLine(varP1, varP3)
            varP3 = CDLPolar(varP1, line16.Angle, dblTieThick * 3#)
            AecDtlApplication.Recipe.SetEntityProperties "cline", blkdef.AddLine(varP1, varP3)
            varP3 = CDLPolar(varP1, Pi * 0.5, dblTieThick * 3#)
            AecDtlApplication.Recipe.SetEntityProperties "cline", blkdef.AddLine(varP1, varP3)
            varP3 = CDLPolar(varP2, line12.Angle + Pi, dblTieThick * 3#)
            AecDtlApplication.Recipe.SetEntityProperties "cline", blkdef.AddLine(varP2, varP3)
            varP2 = line3.EndPoint
            varP3 = CDLPolar(varP2, line17.Angle + Pi, dblTieThick * 3#)
            AecDtlApplication.Recipe.SetEntityProperties "cline", blkdef.AddLine(varP2, varP3)
            varP2 = CDLPolar(line14.EndPoint, CDLAngle(line14.EndPoint, line15.EndPoint), CDLDist(line14.EndPoint, line15.EndPoint) * 0.5)
            varP3 = CDLPolar(varP2, -Pi * 0.5, dblTieThick * 3#)
            AecDtlApplication.Recipe.SetEntityProperties "cline", blkdef.AddLine(varP2, varP3)
    
            varP1 = CDLPolar(line2.EndPoint, Pi, line2.Length * 0.3333333)
            varP2 = CDLPolar(line2.EndPoint, CDLAngle(line2.EndPoint, line3.EndPoint), CDLDist(line2.EndPoint, line3.EndPoint) * 0.3333333)
            varP3 = CDLPolar(varP1, CDLAngle(varP1, varP2) - Pi * 0.5, dblTieThick * 0.5)
            varP4 = CDLPolar(varP2, CDLAngle(varP1, varP2) - Pi * 0.5, dblTieThick * 0.5)
            Set line12 = blkdef.AddLine(varP3, varP4)
            AecDtlApplication.Recipe.SetEntityProperties "rafter", line12
            varP3 = CDLPolar(varP1, CDLAngle(varP1, varP2) + Pi * 0.5, dblTieThick * 0.5)
            varP4 = CDLPolar(varP2, CDLAngle(varP1, varP2) + Pi * 0.5, dblTieThick * 0.5)
            Set line13 = blkdef.AddLine(varP3, varP4)
            AecDtlApplication.Recipe.SetEntityProperties "rafter", line13
    
            varP1 = CDLPolar(line2.EndPoint, Pi, line2.Length * 0.3333333)
            varP2 = varP1
            varP2(1) = varP2(1) + dblSpan
            varP3 = CDLPolar(varP1, CDLAngle(varP1, varP2) - Pi * 0.5, dblTieThick * 0.5)
            varP4 = CDLPolar(varP2, CDLAngle(varP1, varP2) - Pi * 0.5, dblTieThick * 0.5)
            Set line14 = blkdef.AddLine(varP3, varP4)
            AecDtlApplication.Recipe.SetEntityProperties "rafter", line14
            varP3 = CDLPolar(varP1, CDLAngle(varP1, varP2) + Pi * 0.5, dblTieThick * 0.5)
            varP4 = CDLPolar(varP2, CDLAngle(varP1, varP2) + Pi * 0.5, dblTieThick * 0.5)
            Set line15 = blkdef.AddLine(varP3, varP4)
            AecDtlApplication.Recipe.SetEntityProperties "rafter", line15
            
            varP1 = CDLPolar(line2.EndPoint, Pi, line2.Length * 0.3333333)
            varP2 = line3.EndPoint
            varP3 = CDLPolar(varP1, CDLAngle(varP1, varP2) - Pi * 0.5, dblTieThick * 0.5)
            varP4 = CDLPolar(varP2, CDLAngle(varP1, varP2) - Pi * 0.5, dblTieThick * 0.5)
            Set line16 = blkdef.AddLine(varP3, varP4)
            AecDtlApplication.Recipe.SetEntityProperties "rafter", line16
            varP3 = CDLPolar(varP1, CDLAngle(varP1, varP2) + Pi * 0.5, dblTieThick * 0.5)
            varP4 = CDLPolar(varP2, CDLAngle(varP1, varP2) + Pi * 0.5, dblTieThick * 0.5)
            Set line17 = blkdef.AddLine(varP3, varP4)
            AecDtlApplication.Recipe.SetEntityProperties "rafter", line17
    
            varP1 = line12.IntersectWith(line2, acExtendBoth)
            line12.StartPoint = varP1
            varP1 = line13.IntersectWith(line14, acExtendBoth)
            line13.StartPoint = varP1
            varP1 = line16.IntersectWith(line15, acExtendBoth)
            line16.StartPoint = varP1
            varP1 = line17.IntersectWith(line2, acExtendBoth)
            line17.StartPoint = varP1
            varP1 = line12.IntersectWith(line4, acExtendBoth)
            line12.EndPoint = varP1
            varP1 = line13.IntersectWith(line4, acExtendBoth)
            line13.EndPoint = varP1
            varP1 = line14.IntersectWith(line4, acExtendBoth)
            line14.EndPoint = varP1
            varP1 = line15.IntersectWith(line4, acExtendBoth)
            line15.EndPoint = varP1
            varP1 = line16.IntersectWith(line4, acExtendBoth)
            line16.EndPoint = varP1
            varP1 = line17.IntersectWith(line7, acExtendBoth)
            line17.EndPoint = varP1
    
            varP1 = CDLPolar(line2.EndPoint, Pi, line2.Length * 0.3333333)
            varP2 = CDLPolar(line2.EndPoint, CDLAngle(line2.EndPoint, line3.EndPoint), CDLDist(line2.EndPoint, line3.EndPoint) * 0.3333333)
            varP3 = CDLPolar(varP1, line12.Angle, dblTieThick * 3#)
            AecDtlApplication.Recipe.SetEntityProperties "cline", blkdef.AddLine(varP1, varP3)
            varP3 = CDLPolar(varP1, line16.Angle, dblTieThick * 3#)
            AecDtlApplication.Recipe.SetEntityProperties "cline", blkdef.AddLine(varP1, varP3)
            varP3 = CDLPolar(varP1, Pi * 0.5, dblTieThick * 3#)
            AecDtlApplication.Recipe.SetEntityProperties "cline", blkdef.AddLine(varP1, varP3)
            varP3 = CDLPolar(varP2, line12.Angle + Pi, dblTieThick * 3#)
            AecDtlApplication.Recipe.SetEntityProperties "cline", blkdef.AddLine(varP2, varP3)
            varP2 = line3.EndPoint
            varP3 = CDLPolar(varP2, line17.Angle + Pi, dblTieThick * 3#)
            AecDtlApplication.Recipe.SetEntityProperties "cline", blkdef.AddLine(varP2, varP3)
            varP2 = CDLPolar(line14.EndPoint, CDLAngle(line14.EndPoint, line15.EndPoint), CDLDist(line14.EndPoint, line15.EndPoint) * 0.5)
            varP3 = CDLPolar(varP2, -Pi * 0.5, dblTieThick * 3#)
            AecDtlApplication.Recipe.SetEntityProperties "cline", blkdef.AddLine(varP2, varP3)
    
    End Select

    ' start the jig
    Dim status As AecDtlPromptStatus
    status = AecDtlApplication.jig.StampBlock(blkdef)

    ' return the status
    AecDtlApplication.Recipe.ReturnStatus = status

End Sub
Public Sub AecDtlStoneStoneSection()

    Dim dblPnt(0 To 2) As Double
    Dim blkdef As AcadBlock
    Dim blnHatchBrick As Boolean
    Dim dblJoint As Double
    Dim dblHeight As Double
    Dim dblBrickThick As Double
    Dim dblCavityThick As Double
    Dim dblInsThick As Double
    Dim blnInsulation As Boolean
    Dim varP1 As Variant
    
    dblPnt(0) = 0#
    dblPnt(1) = 0#
    dblPnt(2) = 0#
    
    Set blkdef = ThisDrawing.Blocks.Add(dblPnt, "*U")
    
    dblJoint = AecDtlApplication.Database.GetFieldValueDoubleUnitDep("JOINT")
    dblHeight = AecDtlApplication.Database.GetFieldValueDoubleUnitDep("HEIGHT")
    dblBrickThick = AecDtlApplication.Database.GetFieldValueDoubleUnitDep("STONE_THICK")
    
    blnHatchBrick = AecDtlApplication.Palette.GetPropertyValueBool("doStoneHatch")
    blnInsulation = AecDtlApplication.Palette.GetPropertyValueBool("showInsulation")
    dblCavityThick = AecDtlApplication.Palette.GetPropertyValueDoubleUnitDep("CavityThick")
    dblInsThick = AecDtlApplication.Palette.GetPropertyValueDoubleUnitDep("InsThick")

    varP1 = dblPnt
    blkdef.InsertBlock varP1, CreateMortar(dblBrickThick, dblJoint).Name, 1#, 1#, 1#, 0#
    varP1(1) = dblJoint
    blkdef.InsertBlock varP1, CreateBlock(dblBrickThick, dblHeight, blnHatchBrick, "block", "infill").Name, 1#, 1#, 1#, 0#

    varP1 = dblPnt
    varP1(0) = dblBrickThick + dblCavityThick
    blkdef.InsertBlock varP1, CreateMortar(dblBrickThick, dblJoint).Name, 1#, 1#, 1#, 0#
    varP1(1) = varP1(1) + dblJoint
    blkdef.InsertBlock varP1, CreateBlock(dblBrickThick, dblHeight, blnHatchBrick, "block", "infill").Name, 1#, 1#, 1#, 0#
    
    If blnInsulation Then
        varP1(1) = 0#
        blkdef.InsertBlock varP1, CreateInsulation(dblHeight + dblJoint, dblInsThick, "insulation", "", False, False).Name, 1#, 1#, 1#, 0#
    End If

    ' start the jig
    Dim status As AecDtlPromptStatus
    status = AecDtlApplication.jig.LinearArrayBlock(blkdef)

    ' return the status
    AecDtlApplication.Recipe.ReturnStatus = status

End Sub
Public Sub AecDtlStoneBlockSection()

    Dim dblPnt(0 To 2) As Double
    Dim blkdef As AcadBlock
    Dim blnHatchBrick As Boolean
    Dim blnHatchBlock As Boolean
    Dim dblJoint As Double
    Dim dblHeight As Double
    Dim dblBrickThick As Double
    Dim dblBlockThick As Double
    Dim dblCavityThick As Double
    Dim dblInsThick As Double
    Dim blnInsulation As Boolean
    Dim varP1 As Variant
    
    dblPnt(0) = 0#
    dblPnt(1) = 0#
    dblPnt(2) = 0#
    
    Set blkdef = ThisDrawing.Blocks.Add(dblPnt, "*U")
    
    dblJoint = AecDtlApplication.Database.GetFieldValueDoubleUnitDep("JOINT")
    dblHeight = AecDtlApplication.Database.GetFieldValueDoubleUnitDep("HEIGHT")
    dblBrickThick = AecDtlApplication.Database.GetFieldValueDoubleUnitDep("STONE_THICK")
    dblBlockThick = AecDtlApplication.Database.GetFieldValueDoubleUnitDep("BLOCK_THICK")
    
    blnHatchBrick = AecDtlApplication.Palette.GetPropertyValueBool("doStoneHatch")
    blnHatchBlock = AecDtlApplication.Palette.GetPropertyValueBool("doBlockHatch")
    blnInsulation = AecDtlApplication.Palette.GetPropertyValueBool("showInsulation")
    dblCavityThick = AecDtlApplication.Palette.GetPropertyValueDoubleUnitDep("CavityThick")
    dblInsThick = AecDtlApplication.Palette.GetPropertyValueDoubleUnitDep("InsThick")

    varP1 = dblPnt
    blkdef.InsertBlock varP1, CreateMortar(dblBrickThick, dblJoint).Name, 1#, 1#, 1#, 0#
    varP1(1) = dblJoint
    blkdef.InsertBlock varP1, CreateBlock(dblBrickThick, dblHeight, blnHatchBrick, "block", "infill").Name, 1#, 1#, 1#, 0#
    varP1(1) = varP1(1) + dblHeight
    blkdef.InsertBlock varP1, CreateMortar(dblBrickThick, dblJoint).Name, 1#, 1#, 1#, 0#
    varP1(1) = varP1(1) + dblJoint
    blkdef.InsertBlock varP1, CreateBlock(dblBrickThick, dblHeight, blnHatchBrick, "block", "infill").Name, 1#, 1#, 1#, 0#
    varP1(1) = varP1(1) + dblHeight
    blkdef.InsertBlock varP1, CreateMortar(dblBrickThick, dblJoint).Name, 1#, 1#, 1#, 0#
    varP1(1) = varP1(1) + dblJoint
    blkdef.InsertBlock varP1, CreateBlock(dblBrickThick, dblHeight, blnHatchBrick, "block", "infill").Name, 1#, 1#, 1#, 0#

    varP1 = dblPnt
    varP1(0) = dblBrickThick + dblCavityThick
    blkdef.InsertBlock varP1, CreateMortar(dblBlockThick, dblJoint).Name, 1#, 1#, 1#, 0#
    varP1(1) = varP1(1) + dblJoint
    blkdef.InsertBlock varP1, CreateBlock(dblBlockThick, dblHeight * 1.5 + dblJoint * 0.5, blnHatchBlock, "block", "blockinfill").Name, 1#, 1#, 1#, 0#
    varP1(1) = varP1(1) + dblHeight * 1.5 + dblJoint * 0.5
    blkdef.InsertBlock varP1, CreateMortar(dblBlockThick, dblJoint).Name, 1#, 1#, 1#, 0#
    varP1(1) = varP1(1) + dblJoint
    blkdef.InsertBlock varP1, CreateBlock(dblBlockThick, dblHeight * 1.5 + dblJoint * 0.5, blnHatchBlock, "block", "blockinfill").Name, 1#, 1#, 1#, 0#
    
    If blnInsulation Then
        varP1(1) = 0#
        blkdef.InsertBlock varP1, CreateInsulation(dblHeight * 3# + dblJoint * 3#, dblInsThick, "insulation", "", False, False).Name, 1#, 1#, 1#, 0#
    End If

    ' start the jig
    Dim status As AecDtlPromptStatus
    status = AecDtlApplication.jig.LinearArrayBlock(blkdef)

    ' return the status
    AecDtlApplication.Recipe.ReturnStatus = status

End Sub
Public Sub AecDtlBlockBlockSection()

    Dim dblPnt(0 To 2) As Double
    Dim blkdef As AcadBlock
    Dim blnHatchBlock As Boolean
    Dim dblJoint As Double
    Dim dblHeight As Double
    Dim dblBlockThick As Double
    Dim dblCavityThick As Double
    Dim dblInsThick As Double
    Dim blnInsulation As Boolean
    Dim varP1 As Variant
    
    dblPnt(0) = 0#
    dblPnt(1) = 0#
    dblPnt(2) = 0#
    
    Set blkdef = ThisDrawing.Blocks.Add(dblPnt, "*U")
    
    dblJoint = AecDtlApplication.Database.GetFieldValueDoubleUnitDep("JOINT")
    dblHeight = AecDtlApplication.Database.GetFieldValueDoubleUnitDep("HEIGHT")
    dblBlockThick = AecDtlApplication.Database.GetFieldValueDoubleUnitDep("BLOCK_THICK")
    
    blnHatchBlock = AecDtlApplication.Palette.GetPropertyValueBool("doBlockHatch")
    blnInsulation = AecDtlApplication.Palette.GetPropertyValueBool("showInsulation")
    dblCavityThick = AecDtlApplication.Palette.GetPropertyValueDoubleUnitDep("CavityThick")
    dblInsThick = AecDtlApplication.Palette.GetPropertyValueDoubleUnitDep("InsThick")

    varP1 = dblPnt
    blkdef.InsertBlock varP1, CreateMortar(dblBlockThick, dblJoint).Name, 1#, 1#, 1#, 0#
    varP1(1) = dblJoint
    blkdef.InsertBlock varP1, CreateBlock(dblBlockThick, dblHeight, blnHatchBlock, "block", "blockinfill").Name, 1#, 1#, 1#, 0#

    varP1 = dblPnt
    varP1(0) = dblBlockThick + dblCavityThick
    blkdef.InsertBlock varP1, CreateMortar(dblBlockThick, dblJoint).Name, 1#, 1#, 1#, 0#
    varP1(1) = varP1(1) + dblJoint
    blkdef.InsertBlock varP1, CreateBlock(dblBlockThick, dblHeight, blnHatchBlock, "block", "blockinfill").Name, 1#, 1#, 1#, 0#
    
    If blnInsulation Then
        varP1(1) = varP1(1) - dblJoint
        blkdef.InsertBlock varP1, CreateInsulation(dblHeight + dblJoint, dblInsThick, "insulation", "", False, False).Name, 1#, 1#, 1#, 0#
    End If

    ' start the jig
    Dim status As AecDtlPromptStatus
    status = AecDtlApplication.jig.LinearArrayBlock(blkdef)

    ' return the status
    AecDtlApplication.Recipe.ReturnStatus = status

End Sub
Public Sub AecDtlBrickBrickSection()

    Dim dblPnt(0 To 2) As Double
    Dim blkdef As AcadBlock
    Dim blnHatchBrick As Boolean
    Dim dblJoint As Double
    Dim dblHeight As Double
    Dim dblBrickThick As Double
    Dim dblCavityThick As Double
    Dim dblInsThick As Double
    Dim blnInsulation As Boolean
    Dim varP1 As Variant
    
    dblPnt(0) = 0#
    dblPnt(1) = 0#
    dblPnt(2) = 0#
    
    Set blkdef = ThisDrawing.Blocks.Add(dblPnt, "*U")
    
    dblJoint = AecDtlApplication.Database.GetFieldValueDoubleUnitDep("JOINT")
    dblHeight = AecDtlApplication.Database.GetFieldValueDoubleUnitDep("HEIGHT")
    dblBrickThick = AecDtlApplication.Database.GetFieldValueDoubleUnitDep("BRICK_THICK")
    
    blnHatchBrick = AecDtlApplication.Palette.GetPropertyValueBool("doBrickHatch")
    blnInsulation = AecDtlApplication.Palette.GetPropertyValueBool("showInsulation")
    dblCavityThick = AecDtlApplication.Palette.GetPropertyValueDoubleUnitDep("CavityThick")
    dblInsThick = AecDtlApplication.Palette.GetPropertyValueDoubleUnitDep("InsThick")

    varP1 = dblPnt
    blkdef.InsertBlock varP1, CreateMortar(dblBrickThick, dblJoint).Name, 1#, 1#, 1#, 0#
    varP1(1) = dblJoint
    blkdef.InsertBlock varP1, CreateBlock(dblBrickThick, dblHeight, blnHatchBrick, "block", "infill").Name, 1#, 1#, 1#, 0#

    varP1 = dblPnt
    varP1(0) = dblBrickThick + dblCavityThick
    blkdef.InsertBlock varP1, CreateMortar(dblBrickThick, dblJoint).Name, 1#, 1#, 1#, 0#
    varP1(1) = varP1(1) + dblJoint
    blkdef.InsertBlock varP1, CreateBlock(dblBrickThick, dblHeight, blnHatchBrick, "block", "infill").Name, 1#, 1#, 1#, 0#
    
    If blnInsulation Then
        varP1(1) = varP1(1) - dblJoint
        blkdef.InsertBlock varP1, CreateInsulation(dblHeight + dblJoint, dblInsThick, "insulation", "", False, False).Name, 1#, 1#, 1#, 0#
    End If

    ' start the jig
    Dim status As AecDtlPromptStatus
    status = AecDtlApplication.jig.LinearArrayBlock(blkdef)

    ' return the status
    AecDtlApplication.Recipe.ReturnStatus = status

End Sub
Public Sub AecDtlBrickBlockSection()

    Dim dblPnt(0 To 2) As Double
    Dim blkdef As AcadBlock
    Dim blnHatchBrick As Boolean
    Dim blnHatchBlock As Boolean
    Dim dblJoint As Double
    Dim dblHeight As Double
    Dim dblBrickThick As Double
    Dim dblBlockThick As Double
    Dim dblCavityThick As Double
    Dim dblInsThick As Double
    Dim blnInsulation As Boolean
    Dim varP1 As Variant
    
    dblPnt(0) = 0#
    dblPnt(1) = 0#
    dblPnt(2) = 0#
    
    Set blkdef = ThisDrawing.Blocks.Add(dblPnt, "*U")
    
    dblJoint = AecDtlApplication.Database.GetFieldValueDoubleUnitDep("JOINT")
    dblHeight = AecDtlApplication.Database.GetFieldValueDoubleUnitDep("HEIGHT")
    dblBrickThick = AecDtlApplication.Database.GetFieldValueDoubleUnitDep("BRICK_THICK")
    dblBlockThick = AecDtlApplication.Database.GetFieldValueDoubleUnitDep("BLOCK_THICK")
    
    blnHatchBrick = AecDtlApplication.Palette.GetPropertyValueBool("doBrickHatch")
    blnHatchBlock = AecDtlApplication.Palette.GetPropertyValueBool("doBlockHatch")
    blnInsulation = AecDtlApplication.Palette.GetPropertyValueBool("showInsulation")
    dblCavityThick = AecDtlApplication.Palette.GetPropertyValueDoubleUnitDep("CavityThick")
    dblInsThick = AecDtlApplication.Palette.GetPropertyValueDoubleUnitDep("InsThick")

    varP1 = dblPnt
    blkdef.InsertBlock varP1, CreateMortar(dblBrickThick, dblJoint).Name, 1#, 1#, 1#, 0#
    varP1(1) = dblJoint
    blkdef.InsertBlock varP1, CreateBlock(dblBrickThick, dblHeight, blnHatchBrick, "block", "infill").Name, 1#, 1#, 1#, 0#
    varP1(1) = varP1(1) + dblHeight
    blkdef.InsertBlock varP1, CreateMortar(dblBrickThick, dblJoint).Name, 1#, 1#, 1#, 0#
    varP1(1) = varP1(1) + dblJoint
    blkdef.InsertBlock varP1, CreateBlock(dblBrickThick, dblHeight, blnHatchBrick, "block", "infill").Name, 1#, 1#, 1#, 0#
    varP1(1) = varP1(1) + dblHeight
    blkdef.InsertBlock varP1, CreateMortar(dblBrickThick, dblJoint).Name, 1#, 1#, 1#, 0#
    varP1(1) = varP1(1) + dblJoint
    blkdef.InsertBlock varP1, CreateBlock(dblBrickThick, dblHeight, blnHatchBrick, "block", "infill").Name, 1#, 1#, 1#, 0#

    varP1 = dblPnt
    varP1(0) = dblBrickThick + dblCavityThick
    blkdef.InsertBlock varP1, CreateMortar(dblBlockThick, dblJoint).Name, 1#, 1#, 1#, 0#
    varP1(1) = varP1(1) + dblJoint
    blkdef.InsertBlock varP1, CreateBlock(dblBlockThick, dblHeight * 3# + dblJoint * 2#, blnHatchBlock, "block", "blockinfill").Name, 1#, 1#, 1#, 0#
    
    If blnInsulation Then
        varP1(1) = varP1(1) - dblJoint
        blkdef.InsertBlock varP1, CreateInsulation(dblHeight * 3# + dblJoint * 3#, dblInsThick, "insulation", "", False, False).Name, 1#, 1#, 1#, 0#
    End If

    ' start the jig
    Dim status As AecDtlPromptStatus
    status = AecDtlApplication.jig.LinearArrayBlock(blkdef)

    ' return the status
    AecDtlApplication.Recipe.ReturnStatus = status

End Sub
Public Sub AecDtlScreedFlrInsUKSection()

    Dim dblPnt(0 To 2) As Double
    Dim blkdef As AcadBlock
    Dim dblInsThick As Double
    Dim dblFactor As Double
    Dim dblLinear5 As Double
    Dim varP1 As Variant
    Dim varP2 As Variant
    Dim dblSLABTHICK As Double
    Dim dblFloorLength As Double
    Dim blnSlabHatch As Boolean
    Dim line As AcadLine
    Dim dblPInsThick As Double

    dblPnt(0) = 0#
    dblPnt(1) = 0#
    dblPnt(2) = 0#
    
    Set blkdef = ThisDrawing.Blocks.Add(dblPnt, "*U")
    
    dblPInsThick = AecDtlApplication.Database.GetFieldValueDoubleUnitDep("PINS_THICK")

    dblInsThick = AecDtlApplication.Palette.GetPropertyValueDouble("InsThick")
    dblSLABTHICK = AecDtlApplication.Palette.GetPropertyValueDouble("SlabThick")
    dblFloorLength = AecDtlApplication.Palette.GetPropertyValueDouble("FloorLength")
    blnSlabHatch = AecDtlApplication.Palette.GetPropertyValueBool("doSlabHatch")

    dblFactor = AecDtlApplication.Recipe.GetDataValueDoubleUnitDep("Values", "Factor")
    dblLinear5 = 5# * dblFactor

    ' Draw Perimeter Insulation
    varP1 = dblPnt
    varP1(0) = dblPInsThick
    varP1(1) = -dblSLABTHICK
    blkdef.InsertBlock varP1, CreateInsulation(dblSLABTHICK, dblPInsThick - dblLinear5, "insulation", "dpc", True, False).Name, 1#, 1#, 1#, 0#
    ' Draw Slab
    blkdef.InsertBlock varP1, CreateBlock(dblFloorLength - dblPInsThick, dblSLABTHICK, blnSlabHatch, "concreteblock", "concretefloor", True, True, False, True).Name, 1#, 1#, 1#, 0#
    ' Draw Insulation
    varP1(0) = dblLinear5
    varP1(1) = -dblSLABTHICK - dblInsThick + dblLinear5
    blkdef.InsertBlock varP1, CreateInsulation(dblFloorLength - dblLinear5, dblInsThick - dblLinear5, "insulation", "dpc", False, True).Name, 1#, 1#, 1#, -Pi * 0.5
    ' Draw DPC
    varP2 = varP1
    varP2(1) = varP2(1) + dblInsThick - dblLinear5
    Set line = blkdef.AddLine(varP1, varP2)
    AecDtlApplication.Recipe.SetEntityProperties "dpc", line

    ' start the jig
    Dim status As AecDtlPromptStatus
    status = AecDtlApplication.jig.StampBlock(blkdef)

    ' return the status
    AecDtlApplication.Recipe.ReturnStatus = status

End Sub
Public Sub AecDtlGrndBrngFlrInsBUKSection()

    Dim dblPnt(0 To 2) As Double
    Dim blkdef As AcadBlock
    Dim dblInsThick As Double
    Dim dblFactor As Double
    Dim dblLinear5 As Double
    Dim varP1 As Variant
    Dim varP2 As Variant
    Dim varP3 As Variant
    Dim varP4 As Variant
    Dim varP5 As Variant
    Dim varP6 As Variant
    Dim dblSLABTHICK As Double
    Dim dblFloorLength As Double
    Dim blnSlabHatch As Boolean
    Dim dblSANDTHICK As Double
    Dim blnSandHatch As Boolean
    Dim dblWallThick As Double
    Dim dblFootingWidth As Double
    Dim dblDPCHeight As Double
    Dim dblDTOF As Double
    Dim dblHardcoreThick As Double
    Dim dblOffset As Double
    Dim line As AcadLine
    Dim dblPInsThick As Double

    dblPnt(0) = 0#
    dblPnt(1) = 0#
    dblPnt(2) = 0#
    
    Set blkdef = ThisDrawing.Blocks.Add(dblPnt, "*U")
    
    dblPInsThick = AecDtlApplication.Database.GetFieldValueDoubleUnitDep("PINS_THICK")

    dblInsThick = AecDtlApplication.Palette.GetPropertyValueDouble("InsThick")
    dblSLABTHICK = AecDtlApplication.Palette.GetPropertyValueDouble("SlabThick")
    dblFloorLength = AecDtlApplication.Palette.GetPropertyValueDouble("FloorLength")
    dblWallThick = AecDtlApplication.Palette.GetPropertyValueDouble("WallThick")
    dblFootingWidth = AecDtlApplication.Palette.GetPropertyValueDouble("FootingWidth")
    dblDPCHeight = AecDtlApplication.Palette.GetPropertyValueDouble("DPCHeight")
    dblDTOF = AecDtlApplication.Palette.GetPropertyValueDouble("DTOF")
    blnSlabHatch = AecDtlApplication.Palette.GetPropertyValueBool("doSlabHatch")
    dblSANDTHICK = AecDtlApplication.Palette.GetPropertyValueDouble("SandThick")
    blnSandHatch = AecDtlApplication.Palette.GetPropertyValueBool("doSandHatch")
    dblHardcoreThick = AecDtlApplication.Palette.GetPropertyValueDouble("HardcoreThick")

    dblFactor = AecDtlApplication.Recipe.GetDataValueDoubleUnitDep("Values", "Factor")
    dblLinear5 = 5# * dblFactor

    ' Draw Perimeter Insulation
    varP1 = dblPnt
    varP1(0) = dblPInsThick
    varP1(1) = -dblSLABTHICK
    blkdef.InsertBlock varP1, CreateInsulation(dblSLABTHICK, dblPInsThick - dblLinear5, "insulation", "dpc", True, False).Name, 1#, 1#, 1#, 0#
    ' Draw Slab
    blkdef.InsertBlock varP1, CreateBlock(dblFloorLength - dblPInsThick, dblSLABTHICK, blnSlabHatch, "concreteblock", "concretefloor", True, True, False, True).Name, 1#, 1#, 1#, 0#
    ' Draw Insulation
    varP1(0) = dblLinear5
    varP1(1) = -dblSLABTHICK - dblInsThick + dblLinear5
    blkdef.InsertBlock varP1, CreateInsulation(dblFloorLength - dblLinear5, dblInsThick - dblLinear5, "insulation", "dpc", False, True).Name, 1#, 1#, 1#, -Pi * 0.5
    ' Draw DPC
    varP2 = varP1
    varP2(1) = varP2(1) + dblInsThick - dblLinear5
    Set line = blkdef.AddLine(varP1, varP2)
    AecDtlApplication.Recipe.SetEntityProperties "dpc", line
    ' Draw Sand
    varP1(0) = 0#
    varP1(1) = -dblSLABTHICK - dblInsThick - dblSANDTHICK
    blkdef.InsertBlock varP1, CreateBlock(dblFloorLength, dblSANDTHICK, blnSandHatch, "sand", "sandfill", False, True, False, True).Name, 1#, 1#, 1#, 0#
    ' Draw Hardcore
    varP1(0) = -dblWallThick * 0.5 + dblFootingWidth * 0.5
    varP1(1) = -dblDPCHeight - dblDTOF
    dblOffset = (dblDPCHeight + dblDTOF) - (dblSLABTHICK + dblInsThick + dblSANDTHICK + dblHardcoreThick)
    varP2 = varP1
    varP2(0) = varP2(0) + dblOffset
    varP2(1) = varP2(1) + dblOffset
    varP3 = varP1
    varP3(0) = 0#
    varP5 = varP1
    varP5(0) = varP5(0) + (varP2(0) - varP1(0)) * 0.5
    varP5(1) = varP5(1) + (varP2(1) - varP1(1)) * 0.5
    varP4 = varP3
    varP4(0) = varP4(0) + (varP5(0) - varP3(0)) * 0.5
    varP4(1) = -dblSLABTHICK - dblInsThick - dblSANDTHICK
    varP6 = varP4
    varP6(0) = varP5(0) + (varP2(0) - varP5(0)) * 0.5
    Set line = blkdef.AddLine(varP1, varP2)
    AecDtlApplication.Recipe.SetEntityProperties "hardcore", line
    Set line = blkdef.AddLine(varP2, varP6)
    AecDtlApplication.Recipe.SetEntityProperties "hardcore", line
    Set line = blkdef.AddLine(varP6, varP5)
    AecDtlApplication.Recipe.SetEntityProperties "hardcore", line
    Set line = blkdef.AddLine(varP5, varP4)
    AecDtlApplication.Recipe.SetEntityProperties "hardcore", line
    Set line = blkdef.AddLine(varP4, varP3)
    AecDtlApplication.Recipe.SetEntityProperties "hardcore", line
    If dblFloorLength - varP2(0) > 0# Then
        blkdef.InsertBlock varP2, CreateHardcore(dblFloorLength - varP2(0), dblHardcoreThick, "hardcore", "hardcore", False, True).Name, 1#, 1#, 1#, -Pi * 0.5
    End If

    ' start the jig
    Dim status As AecDtlPromptStatus
    status = AecDtlApplication.jig.StampBlock(blkdef)

    ' return the status
    AecDtlApplication.Recipe.ReturnStatus = status

End Sub
Public Sub AecDtlSuspGrndFlrInsBUKSection()

    Dim dblPnt(0 To 2) As Double
    Dim blkdef As AcadBlock
    Dim dblInsThick As Double
    Dim dblFactor As Double
    Dim dblLinear5 As Double
    Dim varP1 As Variant
    Dim varP2 As Variant
    Dim varP3 As Variant
    Dim varP4 As Variant
    Dim varP5 As Variant
    Dim varP6 As Variant
    Dim dblCutBlockWid As Double
    Dim dblSLABTHICK As Double
    Dim dblFloorLength As Double
    Dim blnSlabHatch As Boolean
    Dim dblSANDTHICK As Double
    Dim blnSandHatch As Boolean
    Dim dblWallThick As Double
    Dim dblFootingWidth As Double
    Dim dblDPCHeight As Double
    Dim dblDTOF As Double
    Dim dblHardcoreThick As Double
    Dim dblOffset As Double
    Dim line As AcadLine
    Dim dblPInsThick As Double

    dblPnt(0) = 0#
    dblPnt(1) = 0#
    dblPnt(2) = 0#
    
    Set blkdef = ThisDrawing.Blocks.Add(dblPnt, "*U")
    
    dblPInsThick = AecDtlApplication.Database.GetFieldValueDoubleUnitDep("PINS_THICK")

    dblInsThick = AecDtlApplication.Palette.GetPropertyValueDouble("InsThick")
    dblCutBlockWid = AecDtlApplication.Palette.GetPropertyValueDouble("CutBlockWid")
    dblSLABTHICK = AecDtlApplication.Palette.GetPropertyValueDouble("SlabThick")
    dblFloorLength = AecDtlApplication.Palette.GetPropertyValueDouble("FloorLength")
    dblWallThick = AecDtlApplication.Palette.GetPropertyValueDouble("WallThick")
    dblFootingWidth = AecDtlApplication.Palette.GetPropertyValueDouble("FootingWidth")
    dblDPCHeight = AecDtlApplication.Palette.GetPropertyValueDouble("DPCHeight")
    dblDTOF = AecDtlApplication.Palette.GetPropertyValueDouble("DTOF")
    blnSlabHatch = AecDtlApplication.Palette.GetPropertyValueBool("doSlabHatch")
    dblSANDTHICK = AecDtlApplication.Palette.GetPropertyValueDouble("SandThick")
    blnSandHatch = AecDtlApplication.Palette.GetPropertyValueBool("doSandHatch")
    dblHardcoreThick = AecDtlApplication.Palette.GetPropertyValueDouble("HardcoreThick")

    dblFactor = AecDtlApplication.Recipe.GetDataValueDoubleUnitDep("Values", "Factor")
    dblLinear5 = 5# * dblFactor

    ' Draw Perimeter Insulation
    varP1 = dblPnt
    varP1(0) = dblPInsThick
    varP1(1) = -dblSLABTHICK
    blkdef.InsertBlock varP1, CreateInsulation(dblSLABTHICK, dblPInsThick - dblLinear5, "insulation", "dpc", True, False).Name, 1#, 1#, 1#, 0#
    ' Draw Slab
    blkdef.InsertBlock varP1, CreateBlock(dblFloorLength - dblPInsThick, dblSLABTHICK, blnSlabHatch, "concreteblock", "concretefloor", True, True, False, True).Name, 1#, 1#, 1#, 0#
    ' Draw Insulation
    varP1(0) = dblCutBlockWid
    varP1(1) = -dblSLABTHICK - dblInsThick
    blkdef.InsertBlock varP1, CreateInsulation(dblFloorLength - dblCutBlockWid, dblInsThick - dblLinear5, "insulation", "dpc", True, False).Name, 1#, 1#, 1#, -Pi * 0.5
    ' Draw DPC
    varP1(1) = -dblSLABTHICK - dblLinear5
    varP2 = varP1
    varP2(0) = dblLinear5
    Set line = blkdef.AddLine(varP1, varP2)
    AecDtlApplication.Recipe.SetEntityProperties "dpc", line
    ' Draw Sand
    varP1(0) = dblCutBlockWid
    varP1(1) = -dblSLABTHICK - dblInsThick - dblSANDTHICK
    blkdef.InsertBlock varP1, CreateBlock(dblFloorLength - dblCutBlockWid, dblSANDTHICK, blnSandHatch, "sand", "sandfill", False, True, False, True).Name, 1#, 1#, 1#, 0#
    ' Draw Hardcore
    varP1(0) = dblCutBlockWid - dblWallThick * 0.5 + dblFootingWidth * 0.5
    varP1(1) = -dblDPCHeight - dblDTOF
    dblOffset = (dblDPCHeight + dblDTOF) - (dblSLABTHICK + dblInsThick + dblSANDTHICK + dblHardcoreThick)
    varP2 = varP1
    varP2(0) = varP2(0) + dblOffset
    varP2(1) = varP2(1) + dblOffset
    varP3 = varP1
    varP3(0) = dblCutBlockWid
    varP5 = varP1
    varP5(0) = varP5(0) + (varP2(0) - varP1(0)) * 0.5
    varP5(1) = varP5(1) + (varP2(1) - varP1(1)) * 0.5
    varP4 = varP3
    varP4(0) = varP4(0) + (varP5(0) - varP3(0)) * 0.5
    varP4(1) = -dblSLABTHICK - dblInsThick - dblSANDTHICK
    varP6 = varP4
    varP6(0) = varP5(0) + (varP2(0) - varP5(0)) * 0.5
    Set line = blkdef.AddLine(varP1, varP2)
    AecDtlApplication.Recipe.SetEntityProperties "hardcore", line
    Set line = blkdef.AddLine(varP2, varP6)
    AecDtlApplication.Recipe.SetEntityProperties "hardcore", line
    Set line = blkdef.AddLine(varP6, varP5)
    AecDtlApplication.Recipe.SetEntityProperties "hardcore", line
    Set line = blkdef.AddLine(varP5, varP4)
    AecDtlApplication.Recipe.SetEntityProperties "hardcore", line
    Set line = blkdef.AddLine(varP4, varP3)
    AecDtlApplication.Recipe.SetEntityProperties "hardcore", line
    If dblFloorLength - varP2(0) > 0# Then
        blkdef.InsertBlock varP2, CreateHardcore(dblFloorLength - varP2(0), dblHardcoreThick, "hardcore", "hardcore", False, True).Name, 1#, 1#, 1#, -Pi * 0.5
    End If

    ' start the jig
    Dim status As AecDtlPromptStatus
    status = AecDtlApplication.jig.StampBlock(blkdef)

    ' return the status
    AecDtlApplication.Recipe.ReturnStatus = status

End Sub
Public Sub AecDtlGrndBrngFlrInsAUKSection()

    Dim dblPnt(0 To 2) As Double
    Dim blkdef As AcadBlock
    Dim dblFloorThick As Double
    Dim dblInsThick As Double
    Dim dblFactor As Double
    Dim dblLinear5 As Double
    Dim dblLinear10 As Double
    Dim varP1 As Variant
    Dim varP2 As Variant
    Dim varP3 As Variant
    Dim varP4 As Variant
    Dim varP5 As Variant
    Dim varP6 As Variant
    Dim dblSLABTHICK As Double
    Dim dblFloorLength As Double
    Dim blnSlabHatch As Boolean
    Dim dblWallThick As Double
    Dim dblFootingWidth As Double
    Dim dblDPCHeight As Double
    Dim dblDTOF As Double
    Dim dblHardcoreThick As Double
    Dim dblOffset As Double
    Dim line As AcadLine

    dblPnt(0) = 0#
    dblPnt(1) = 0#
    dblPnt(2) = 0#
    
    Set blkdef = ThisDrawing.Blocks.Add(dblPnt, "*U")
    
    dblFloorThick = AecDtlApplication.Palette.GetPropertyValueDouble("FloorThick")
    dblInsThick = AecDtlApplication.Palette.GetPropertyValueDouble("InsThick")
    dblSLABTHICK = AecDtlApplication.Palette.GetPropertyValueDouble("SlabThick")
    dblFloorLength = AecDtlApplication.Palette.GetPropertyValueDouble("FloorLength")
    dblWallThick = AecDtlApplication.Palette.GetPropertyValueDouble("WallThick")
    dblFootingWidth = AecDtlApplication.Palette.GetPropertyValueDouble("FootingWidth")
    dblDPCHeight = AecDtlApplication.Palette.GetPropertyValueDouble("DPCHeight")
    dblDTOF = AecDtlApplication.Palette.GetPropertyValueDouble("DTOF")
    blnSlabHatch = AecDtlApplication.Palette.GetPropertyValueBool("doSlabHatch")
    dblHardcoreThick = AecDtlApplication.Palette.GetPropertyValueDouble("HardcoreThick")

    dblFactor = AecDtlApplication.Recipe.GetDataValueDoubleUnitDep("Values", "Factor")
    dblLinear5 = 5# * dblFactor
    dblLinear10 = 10# * dblFactor

    ' Draw Slab
    varP1 = dblPnt
    varP1(1) = -dblFloorThick - dblInsThick - dblSLABTHICK
    blkdef.InsertBlock varP1, CreateBlock(dblFloorLength, dblSLABTHICK, blnSlabHatch, "concreteblock", "concretefloor", True, True, False, True).Name, 1#, 1#, 1#, 0#
    ' Draw Insulation
    varP1(0) = dblLinear5
    varP1(1) = -dblFloorThick - dblInsThick + dblLinear5
    blkdef.InsertBlock varP1, CreateInsulation(dblFloorLength - dblLinear5, dblInsThick - dblLinear10, "insulation", "dpc", True, True).Name, 1#, 1#, 1#, -Pi * 0.5
    ' Draw DPC
    varP2 = dblPnt
    varP2(0) = dblLinear5
    Set line = blkdef.AddLine(varP1, varP2)
    AecDtlApplication.Recipe.SetEntityProperties "dpc", line
    ' Draw Floor
    varP1(0) = dblLinear10
    varP1(1) = -dblFloorThick
    blkdef.InsertBlock varP1, CreateBlock(dblFloorLength - dblLinear10, dblFloorThick, False, "floor", "", True, True, False, True).Name, 1#, 1#, 1#, 0#
    ' Draw Hardcore
    varP1(0) = -dblWallThick * 0.5 + dblFootingWidth * 0.5
    varP1(1) = -dblDPCHeight - dblDTOF
    dblOffset = (dblDPCHeight + dblDTOF) - (dblFloorThick + dblInsThick + dblSLABTHICK + dblHardcoreThick)
    varP2 = varP1
    varP2(0) = varP2(0) + dblOffset
    varP2(1) = varP2(1) + dblOffset
    varP3 = varP1
    varP3(0) = 0#
    varP5 = varP1
    varP5(0) = varP5(0) + (varP2(0) - varP1(0)) * 0.5
    varP5(1) = varP5(1) + (varP2(1) - varP1(1)) * 0.5
    varP4 = varP3
    varP4(0) = varP4(0) + (varP5(0) - varP3(0)) * 0.5
    varP4(1) = varP2(1) + dblHardcoreThick
    varP6 = varP4
    varP6(0) = varP5(0) + (varP2(0) - varP5(0)) * 0.5
    Set line = blkdef.AddLine(varP1, varP2)
    AecDtlApplication.Recipe.SetEntityProperties "hardcore", line
    Set line = blkdef.AddLine(varP2, varP6)
    AecDtlApplication.Recipe.SetEntityProperties "hardcore", line
    Set line = blkdef.AddLine(varP6, varP5)
    AecDtlApplication.Recipe.SetEntityProperties "hardcore", line
    Set line = blkdef.AddLine(varP5, varP4)
    AecDtlApplication.Recipe.SetEntityProperties "hardcore", line
    Set line = blkdef.AddLine(varP4, varP3)
    AecDtlApplication.Recipe.SetEntityProperties "hardcore", line
    If dblFloorLength - varP2(0) > 0# Then
        blkdef.InsertBlock varP2, CreateHardcore(dblFloorLength - varP2(0), dblHardcoreThick, "hardcore", "hardcore", False, True).Name, 1#, 1#, 1#, -Pi * 0.5
    End If

    ' start the jig
    Dim status As AecDtlPromptStatus
    status = AecDtlApplication.jig.StampBlock(blkdef)

    ' return the status
    AecDtlApplication.Recipe.ReturnStatus = status

End Sub
Public Sub AecDtlSuspGrndFlrInsAUKSection()

    Dim dblPnt(0 To 2) As Double
    Dim blkdef As AcadBlock
    Dim dblFloorThick As Double
    Dim dblInsThick As Double
    Dim dblFactor As Double
    Dim dblLinear5 As Double
    Dim dblLinear10 As Double
    Dim dblMortarThick As Double
    Dim varP1 As Variant
    Dim varP2 As Variant
    Dim varP3 As Variant
    Dim varP4 As Variant
    Dim varP5 As Variant
    Dim varP6 As Variant
    Dim dblInnerThick As Double
    Dim dblSLABTHICK As Double
    Dim dblFloorLength As Double
    Dim blnSlabHatch As Boolean
    Dim dblSANDTHICK As Double
    Dim blnSandHatch As Boolean
    Dim dblWallThick As Double
    Dim dblFootingWidth As Double
    Dim dblDPCHeight As Double
    Dim dblDTOF As Double
    Dim dblHardcoreThick As Double
    Dim dblOffset As Double
    Dim line As AcadLine

    dblPnt(0) = 0#
    dblPnt(1) = 0#
    dblPnt(2) = 0#
    
    Set blkdef = ThisDrawing.Blocks.Add(dblPnt, "*U")
    
    dblFloorThick = AecDtlApplication.Palette.GetPropertyValueDouble("FloorThick")
    dblInsThick = AecDtlApplication.Palette.GetPropertyValueDouble("InsThick")
    dblMortarThick = AecDtlApplication.Palette.GetPropertyValueDouble("MortarThick")
    dblInnerThick = AecDtlApplication.Palette.GetPropertyValueDouble("InnerThick")
    dblSLABTHICK = AecDtlApplication.Palette.GetPropertyValueDouble("SlabThick")
    dblFloorLength = AecDtlApplication.Palette.GetPropertyValueDouble("FloorLength")
    dblWallThick = AecDtlApplication.Palette.GetPropertyValueDouble("WallThick")
    dblFootingWidth = AecDtlApplication.Palette.GetPropertyValueDouble("FootingWidth")
    dblDPCHeight = AecDtlApplication.Palette.GetPropertyValueDouble("DPCHeight")
    dblDTOF = AecDtlApplication.Palette.GetPropertyValueDouble("DTOF")
    blnSlabHatch = AecDtlApplication.Palette.GetPropertyValueBool("doSlabHatch")
    dblSANDTHICK = AecDtlApplication.Palette.GetPropertyValueDouble("SandThick")
    blnSandHatch = AecDtlApplication.Palette.GetPropertyValueBool("doSandHatch")
    dblHardcoreThick = AecDtlApplication.Palette.GetPropertyValueDouble("HardcoreThick")

    dblFactor = AecDtlApplication.Recipe.GetDataValueDoubleUnitDep("Values", "Factor")
    dblLinear5 = 5# * dblFactor
    dblLinear10 = 10# * dblFactor

    ' Draw DPC
    varP1 = dblPnt
    varP1(1) = dblMortarThick - dblLinear5
    blkdef.InsertBlock varP1, CreateBlock(dblInnerThick, dblSLABTHICK + dblLinear10, False, "dpc", "", True, True, False, False).Name, 1#, 1#, 1#, 0#
    blkdef.InsertBlock varP1, CreateBlock(dblInnerThick + dblFloorLength, dblSLABTHICK + dblLinear10, False, "dpc", "", False, False, False, True).Name, 1#, 1#, 1#, 0#
    ' Draw Slab
    varP1(0) = varP1(0) + dblLinear5
    varP1(1) = varP1(1) + dblLinear5
    blkdef.InsertBlock varP1, CreateBlock(dblInnerThick + dblFloorLength - dblLinear5, dblSLABTHICK, blnSlabHatch, "concreteblock", "concretefloor", True, True, False, True).Name, 1#, 1#, 1#, 0#
    ' Draw Insulation
    varP1(0) = dblInnerThick
    varP1(1) = dblSLABTHICK + dblMortarThick
    blkdef.InsertBlock varP1, CreateInsulation(dblFloorLength, dblInsThick - dblLinear5, "insulation", "dpc", True, False).Name, 1#, 1#, 1#, -Pi * 0.5
    ' Draw Floor
    varP1(0) = varP1(0) + dblLinear5
    varP1(1) = varP1(1) + dblInsThick
    blkdef.InsertBlock varP1, CreateBlock(dblFloorLength - dblLinear5, dblFloorThick, False, "floor", "", True, True, False, True).Name, 1#, 1#, 1#, 0#
    ' Draw Sand
    varP1(0) = dblInnerThick
    varP1(1) = dblMortarThick - dblSANDTHICK
    blkdef.InsertBlock varP1, CreateBlock(dblFloorLength, dblSANDTHICK - dblLinear5, blnSandHatch, "sand", "sandfill", False, False, False, True).Name, 1#, 1#, 1#, 0#
    ' Draw Hardcore
    varP1(0) = dblInnerThick - dblWallThick * 0.5 + dblFootingWidth * 0.5
    varP1(1) = dblMortarThick + dblSLABTHICK - dblDPCHeight - dblDTOF
    dblOffset = Abs((dblMortarThick + dblSLABTHICK - dblDPCHeight - dblDTOF) - (dblMortarThick - dblSANDTHICK - dblHardcoreThick))
    varP2 = varP1
    varP2(0) = varP2(0) + dblOffset
    varP2(1) = varP2(1) + dblOffset
    varP3 = varP1
    varP3(0) = dblInnerThick
    varP5 = varP1
    varP5(0) = varP5(0) + (varP2(0) - varP1(0)) * 0.5
    varP5(1) = varP5(1) + (varP2(1) - varP1(1)) * 0.5
    varP4 = varP3
    varP4(0) = varP4(0) + (varP5(0) - varP3(0)) * 0.5
    varP4(1) = dblMortarThick - dblSANDTHICK
    varP6 = varP4
    varP6(0) = varP5(0) + (varP2(0) - varP5(0)) * 0.5
    Set line = blkdef.AddLine(varP1, varP2)
    AecDtlApplication.Recipe.SetEntityProperties "hardcore", line
    Set line = blkdef.AddLine(varP2, varP6)
    AecDtlApplication.Recipe.SetEntityProperties "hardcore", line
    Set line = blkdef.AddLine(varP6, varP5)
    AecDtlApplication.Recipe.SetEntityProperties "hardcore", line
    Set line = blkdef.AddLine(varP5, varP4)
    AecDtlApplication.Recipe.SetEntityProperties "hardcore", line
    Set line = blkdef.AddLine(varP4, varP3)
    AecDtlApplication.Recipe.SetEntityProperties "hardcore", line
    If dblFloorLength - varP2(0) + dblInnerThick > 0# Then
        blkdef.InsertBlock varP2, CreateHardcore(dblFloorLength - varP2(0) + dblInnerThick, Abs(varP2(1)) - dblSANDTHICK + dblMortarThick, "hardcore", "hardcore", False, True).Name, 1#, 1#, 1#, -Pi * 0.5
    End If

    ' start the jig
    Dim status As AecDtlPromptStatus
    status = AecDtlApplication.jig.StampBlock(blkdef)

    ' return the status
    AecDtlApplication.Recipe.ReturnStatus = status

End Sub
Public Sub AecDtlTimberFloorUKSection()

    Dim dblPnt(0 To 2) As Double
    Dim blkDefStart As AcadBlock
    Dim blkDefNext As AcadBlock
    Dim dblPInsThick As Double
    Dim dblFloorThick As Double
    Dim dblInsThick As Double
    Dim dblJoistWidth As Double
    Dim dblJoistDepth As Double
    Dim dblJoistSpace As Double
    Dim dblSubFloorVoid As Double
    Dim dblSubFloorThick As Double
    Dim blnSubFloorHatch As Boolean
    Dim dblFactor As Double
    Dim dblLinear5 As Double
    Dim dblBatternWidth As Double
    Dim dblBatternDepth As Double
    Dim varP1 As Variant
    Dim varP2 As Variant
    Dim varP3 As Variant
    Dim varP4 As Variant
    Dim line As AcadLine
    
    dblPnt(0) = 0#
    dblPnt(1) = 0#
    dblPnt(2) = 0#
    
    Set blkDefStart = ThisDrawing.Blocks.Add(dblPnt, "*U")
    Set blkDefNext = ThisDrawing.Blocks.Add(dblPnt, "*U")
    
    dblPInsThick = AecDtlApplication.Database.GetFieldValueDoubleUnitDep("PINS_THICK")

    dblFloorThick = AecDtlApplication.Palette.GetPropertyValueDouble("FloorThick")
    dblInsThick = AecDtlApplication.Palette.GetPropertyValueDouble("InsThick")
    dblJoistWidth = AecDtlApplication.Palette.GetPropertyValueDouble("JoistWidth")
    dblJoistDepth = AecDtlApplication.Palette.GetPropertyValueDouble("JoistDepth")
    dblJoistSpace = AecDtlApplication.Palette.GetPropertyValueDouble("JoistSpace")
    dblSubFloorVoid = AecDtlApplication.Palette.GetPropertyValueDouble("SubFloorVoid")
    dblSubFloorThick = AecDtlApplication.Palette.GetPropertyValueDouble("SubFloorThick")
    blnSubFloorHatch = AecDtlApplication.Palette.GetPropertyValueBool("doSubFloorHatch")

    dblFactor = AecDtlApplication.Recipe.GetDataValueDoubleUnitDep("Values", "Factor")
    dblBatternWidth = AecDtlApplication.Recipe.GetDataValueDoubleUnitDep("Values", "BatternWidth")
    dblBatternDepth = AecDtlApplication.Recipe.GetDataValueDoubleUnitDep("Values", "BatternDepth")
    dblLinear5 = 5# * dblFactor
    
    ' Create First Block
    ' Create Finished Floor
    varP1 = dblPnt
    varP1(0) = dblLinear5
    varP1(1) = -dblFloorThick
    blkDefStart.InsertBlock varP1, CreateBlock(dblPInsThick + dblJoistWidth - dblLinear5, dblFloorThick, False, "floor", "", True, True, False, True).Name, 1#, 1#, 1#, 0#
    ' Create Joist
    varP4 = dblPnt
    varP4(0) = dblPInsThick + dblJoistWidth - dblJoistWidth
    varP4(1) = -dblFloorThick
    blkDefStart.InsertBlock varP4, CreateTimberSection(dblJoistWidth, dblJoistDepth, "beams").Name, 1#, 1#, 1#, 0#
    ' Create Perimeter Insulation
    varP4(0) = 0#
    blkDefStart.InsertBlock varP4, CreateInsulation(dblJoistDepth, dblPInsThick, "insulation", "", False, False).Name, 1#, 1#, 1#, -Pi
    ' Create DPC
    varP1 = dblPnt
    varP1(1) = -dblFloorThick - dblJoistDepth - dblSubFloorVoid
    varP2 = varP1
    varP2(1) = varP2(1) - dblSubFloorThick - dblLinear5
    varP3 = varP2
    varP3(0) = varP3(0) + dblPInsThick + dblJoistWidth
    Set line = blkDefStart.AddLine(varP1, varP2)
    AecDtlApplication.Recipe.SetEntityProperties "dpc", line
    Set line = blkDefStart.AddLine(varP2, varP3)
    AecDtlApplication.Recipe.SetEntityProperties "dpc", line
    ' Create Concrete Sub Floor
    varP1(1) = varP1(1) - dblSubFloorThick
    blkDefStart.InsertBlock varP1, CreateBlock(dblPInsThick + dblJoistWidth, dblSubFloorThick, blnSubFloorHatch, "concreteblock", "concretefloor", False, True, False, True).Name, 1#, 1#, 1#, 0#
    
    ' Create Next Block
    ' Create Finished Floor
    varP1 = dblPnt
    varP1(1) = -dblFloorThick
    blkDefNext.InsertBlock varP1, CreateBlock(dblJoistSpace, dblFloorThick, False, "floor", "", False, True, False, True).Name, 1#, 1#, 1#, 0#
    ' Create Insulation
    varP1 = dblPnt
    varP1(1) = -dblFloorThick - dblInsThick
    blkDefNext.InsertBlock varP1, CreateInsulation(dblJoistSpace - dblJoistWidth, dblInsThick, "insulation", "", False, False).Name, 1#, 1#, 1#, -Pi * 0.5
    ' Create Joist
    varP4 = dblPnt
    varP4(0) = dblJoistSpace - dblJoistWidth
    varP4(1) = -dblFloorThick
    blkDefNext.InsertBlock varP4, CreateTimberSection(dblJoistWidth, dblJoistDepth, "beams").Name, 1#, 1#, 1#, 0#
    ' Create Batterns
    varP4(0) = varP4(0) - dblBatternWidth
    varP4(1) = varP4(1) - dblInsThick
    blkDefNext.InsertBlock varP4, CreateTimberSection(dblBatternWidth, dblBatternDepth, "beams").Name, 1#, 1#, 1#, 0#
    varP4(0) = 0#
    blkDefNext.InsertBlock varP4, CreateTimberSection(dblBatternWidth, dblBatternDepth, "beams").Name, 1#, 1#, 1#, 0#
    ' Create DPC
    varP1 = dblPnt
    varP1(1) = -dblFloorThick - dblJoistDepth - dblSubFloorVoid - dblLinear5 - dblSubFloorThick
    varP2 = varP1
    varP2(0) = varP2(0) + dblJoistSpace
    Set line = blkDefNext.AddLine(varP1, varP2)
    AecDtlApplication.Recipe.SetEntityProperties "dpc", line
    ' Create Concrete Sub Floor
    varP1 = dblPnt
    varP1(1) = -dblFloorThick - dblJoistDepth - dblSubFloorVoid - dblSubFloorThick
    blkDefNext.InsertBlock varP1, CreateBlock(dblJoistSpace, dblSubFloorThick, blnSubFloorHatch, "concreteblock", "concretefloor", False, True, False, True).Name, 1#, 1#, 1#, 0#
    
    ' start the jig
    Dim status As AecDtlPromptStatus
    status = AecDtlApplication.jig.BookendsBlock(blkDefStart, blkDefNext, blkDefNext)

    ' return the status
    AecDtlApplication.Recipe.ReturnStatus = status

End Sub
Public Sub AecDtlBeamBlockCFlrUKSection()

    Dim dblPnt(0 To 2) As Double
    Dim blkDefStart As AcadBlock
    Dim blkDefNext As AcadBlock
    Dim blkDefEnd As AcadBlock
    Dim dblSpacerProj As Double
    Dim dblSpacerGap As Double
    Dim dblBlockThick As Double
    Dim dblFloorThick As Double
    Dim dblInsThick As Double
    Dim dblPInsThick As Double
    Dim dblBlockSize As Double
    Dim intBeamType As Integer
    Dim blnBlockHatch As Boolean
    Dim blnFloorHatch As Boolean
    Dim dblOffset As Double
    Dim varP1 As Variant
    Dim varP2 As Variant
    Dim line As AcadLine
    Dim dblFactor As Double
    Dim dblLinear5 As Double
    Dim dblLinear10 As Double
    Dim dblLinear15 As Double
    
    On Error Resume Next

    dblPnt(0) = 0#
    dblPnt(1) = 0#
    dblPnt(2) = 0#
    
    Set blkDefStart = ThisDrawing.Blocks.Add(dblPnt, "*U")
    Set blkDefNext = ThisDrawing.Blocks.Add(dblPnt, "*U")
    Set blkDefEnd = ThisDrawing.Blocks.Add(dblPnt, "*U")
    
    dblBlockThick = AecDtlApplication.Database.GetFieldValueDoubleUnitDep("BLOCK_THICK")
    dblBlockSize = AecDtlApplication.Database.GetFieldValueDoubleUnitDep("BLOCK_SIZE")
    dblPInsThick = AecDtlApplication.Database.GetFieldValueDoubleUnitDep("PINS_THICK")
    
    blnBlockHatch = AecDtlApplication.Palette.GetPropertyValueBool("doBlockHatch")
    blnFloorHatch = AecDtlApplication.Palette.GetPropertyValueBool("doFloorHatch")
    intBeamType = Val(AecDtlApplication.Palette.GetPropertyValueStr("BeamType"))
    dblFloorThick = AecDtlApplication.Palette.GetPropertyValueDouble("FloorThick")
    dblInsThick = AecDtlApplication.Palette.GetPropertyValueDouble("InsThick")
    dblSpacerGap = AecDtlApplication.Palette.GetPropertyValueDouble("SpacerGap")
    dblSpacerProj = AecDtlApplication.Palette.GetPropertyValueDouble("SpacerProj")
    
    dblFactor = AecDtlApplication.Recipe.GetDataValueDoubleUnitDep("Values", "Factor")
    dblLinear5 = 5# * dblFactor
    dblLinear10 = 10# * dblFactor
    dblLinear15 = 15# * dblFactor

    If intBeamType = 0 Then
        dblOffset = 40.5 * dblFactor
    Else
        dblOffset = 49# * dblFactor
    End If
    
    ' Create Start Block
    ' Create Beam section
    dblPnt(0) = dblSpacerProj + dblSpacerGap
    blkDefStart.InsertBlock dblPnt, CreateBeamSection(intBeamType, dblBlockThick).Name, 1#, 1#, 1#, 0#
    ' Create Infill Blocks
    dblPnt(0) = 0#
    blkDefStart.InsertBlock dblPnt, CreateBlock(dblSpacerProj + dblSpacerGap, dblBlockThick, blnBlockHatch, "block", "blockinfill").Name, 1#, 1#, 1#, 0#
    ' Create DPC Lines
    varP1 = dblPnt
    varP1(1) = dblBlockThick + dblLinear5
    varP2 = varP1
    varP2(0) = varP2(0) + dblSpacerProj
    Set line = blkDefStart.AddLine(varP1, varP2)
    AecDtlApplication.Recipe.SetEntityProperties "dpc", line
    varP1 = varP2
    varP1(0) = varP1(0) + dblLinear5
    varP1(1) = varP1(1) + dblLinear5
    Set line = blkDefStart.AddLine(varP2, varP1)
    AecDtlApplication.Recipe.SetEntityProperties "dpc", line
    varP2 = varP1
    varP2(0) = dblOffset + dblSpacerProj + dblSpacerGap
    Set line = blkDefStart.AddLine(varP1, varP2)
    AecDtlApplication.Recipe.SetEntityProperties "dpc", line
    varP2(1) = varP2(1) - dblLinear5
    varP1 = varP2
    varP1(0) = dblSpacerProj + dblLinear5
    Set line = blkDefStart.AddLine(varP1, varP2)
    AecDtlApplication.Recipe.SetEntityProperties "dpc", line
    ' Create Perimeter Insulation
    varP1(0) = dblPInsThick + dblSpacerProj
    varP1(1) = dblBlockThick + dblLinear10
    blkDefStart.InsertBlock varP1, CreateInsulation(dblFloorThick + dblInsThick - dblLinear10, dblPInsThick, "insulation", "", False, False).Name, 1#, 1#, 1#, 0#
    ' Create Insulation
    blkDefStart.InsertBlock varP1, CreateInsulation((dblSpacerGap + dblOffset) - (dblPInsThick), dblInsThick - dblLinear15, "insulation", "dpc", True, False).Name, 1#, 1#, 1#, -Pi * 0.5
    ' Create Concrete Screed
    varP1(1) = dblBlockThick + dblInsThick + dblFloorThick
    blkDefStart.InsertBlock varP1, CreateBlock(dblFloorThick, (dblSpacerGap + dblOffset) - (dblPInsThick), blnFloorHatch, "floor", "concretefloor", True, False, True, True).Name, 1#, 1#, 1#, -Pi * 0.5
    
    ' Create Intermediate Block
    ' Create Beam section
    dblPnt(0) = dblOffset
    blkDefNext.InsertBlock dblPnt, CreateBeamSection(intBeamType, dblBlockThick).Name, -1#, 1#, 1#, 0#
    dblPnt(0) = dblOffset + dblBlockSize
    blkDefNext.InsertBlock dblPnt, CreateBeamSection(intBeamType, dblBlockThick).Name, 1#, 1#, 1#, 0#
    ' Create Infill Blocks
    dblPnt(0) = dblOffset
    blkDefNext.InsertBlock dblPnt, CreateBlock(dblBlockSize, dblBlockThick, blnBlockHatch, "block", "blockinfill").Name, 1#, 1#, 1#, 0#
    ' Create DPC Lines
    dblPnt(0) = 0#
    varP1 = dblPnt
    varP1(0) = 0#
    varP1(1) = dblBlockThick + dblLinear5
    varP2 = varP1
    varP2(0) = dblBlockSize + dblOffset * 2#
    Set line = blkDefNext.AddLine(varP1, varP2)
    AecDtlApplication.Recipe.SetEntityProperties "dpc", line
    ' Create Insulation
    varP1(0) = 0
    varP1(1) = dblBlockThick + dblLinear10
    blkDefNext.InsertBlock varP1, CreateInsulation(dblBlockSize + dblOffset * 2#, dblInsThick - dblLinear15, "insulation", "dpc", True, False).Name, 1#, 1#, 1#, -Pi * 0.5
    ' Create Concrete Screed
    varP1(1) = dblBlockThick + dblInsThick + dblFloorThick
    blkDefNext.InsertBlock varP1, CreateBlock(dblFloorThick, dblBlockSize + dblOffset * 2#, blnFloorHatch, "floor", "concretefloor", True, False, True, False).Name, 1#, 1#, 1#, -Pi * 0.5

    ' Create End Block
    ' Create Beam section
    dblPnt(0) = dblOffset
    blkDefEnd.InsertBlock dblPnt, CreateBeamSection(intBeamType, dblBlockThick).Name, -1#, 1#, 1#, 0#
    ' Create Infill Blocks
    blkDefEnd.InsertBlock dblPnt, CreateBlock(dblBlockSize, dblBlockThick, blnBlockHatch, "block", "blockinfill").Name, 1#, 1#, 1#, 0#
    ' Create DPC Lines
    dblPnt(0) = 0#
    varP1 = dblPnt
    varP1(0) = 0#
    varP1(1) = dblBlockThick + dblLinear5
    varP2 = varP1
    varP2(0) = dblBlockSize + dblOffset
    Set line = blkDefEnd.AddLine(varP1, varP2)
    AecDtlApplication.Recipe.SetEntityProperties "dpc", line
    ' Create Insulation
    varP1(0) = 0
    varP1(1) = dblBlockThick + dblLinear10
    blkDefEnd.InsertBlock varP1, CreateInsulation(dblBlockSize + dblOffset, dblInsThick - dblLinear15, "insulation", "dpc", True, False).Name, 1#, 1#, 1#, -Pi * 0.5
    ' Create Concrete Screed
    varP1(1) = dblBlockThick + dblInsThick + dblFloorThick
    blkDefEnd.InsertBlock varP1, CreateBlock(dblFloorThick, dblBlockSize + dblOffset, blnFloorHatch, "floor", "concretefloor", True, False, True, False).Name, 1#, 1#, 1#, -Pi * 0.5

    ' start the jig
    Dim status As AecDtlPromptStatus
    status = AecDtlApplication.jig.BookendsBlock(blkDefStart, blkDefEnd, blkDefNext)

    ' return the status
    AecDtlApplication.Recipe.ReturnStatus = status

End Sub
Public Sub AecDtlBeamBlockTFlrUKSection()

    Dim dblPnt(0 To 2) As Double
    Dim blkDefStart As AcadBlock
    Dim blkDefNext As AcadBlock
    Dim blkDefEnd As AcadBlock
    Dim dblSpacerProj As Double
    Dim dblSpacerGap As Double
    Dim dblBlockThick As Double
    Dim dblFloorThick As Double
    Dim dblInsThick As Double
    Dim dblBlockSize As Double
    Dim intBeamType As Integer
    Dim blnBlockHatch As Boolean
    Dim dblOffset As Double
    Dim varP1 As Variant
    Dim varP2 As Variant
    Dim line As AcadLine
    Dim dblFactor As Double
    Dim dblLinear5 As Double
    Dim dblLinear10 As Double
    Dim dblLinear15 As Double
    
    On Error Resume Next

    dblPnt(0) = 0#
    dblPnt(1) = 0#
    dblPnt(2) = 0#
    
    Set blkDefStart = ThisDrawing.Blocks.Add(dblPnt, "*U")
    Set blkDefNext = ThisDrawing.Blocks.Add(dblPnt, "*U")
    Set blkDefEnd = ThisDrawing.Blocks.Add(dblPnt, "*U")
    
    dblBlockThick = AecDtlApplication.Database.GetFieldValueDoubleUnitDep("BLOCK_THICK")
    dblBlockSize = AecDtlApplication.Database.GetFieldValueDoubleUnitDep("BLOCK_SIZE")
    
    blnBlockHatch = AecDtlApplication.Palette.GetPropertyValueBool("doBlockHatch")
    intBeamType = Val(AecDtlApplication.Palette.GetPropertyValueStr("BeamType"))
    dblFloorThick = AecDtlApplication.Palette.GetPropertyValueDouble("FloorThick")
    dblInsThick = AecDtlApplication.Palette.GetPropertyValueDouble("InsThick")
    dblSpacerGap = AecDtlApplication.Palette.GetPropertyValueDouble("SpacerGap")
    dblSpacerProj = AecDtlApplication.Palette.GetPropertyValueDouble("SpacerProj")
    
    dblFactor = AecDtlApplication.Recipe.GetDataValueDoubleUnitDep("Values", "Factor")
    dblLinear5 = 5# * dblFactor
    dblLinear10 = 10# * dblFactor
    dblLinear15 = 15# * dblFactor

    If intBeamType = 0 Then
        dblOffset = 40.5 * dblFactor
    Else
        dblOffset = 49# * dblFactor
    End If
    
    ' Create Start Block
    ' Create Beam
    dblPnt(0) = dblSpacerProj + dblSpacerGap
    blkDefStart.InsertBlock dblPnt, CreateBeamSection(intBeamType, dblBlockThick).Name, 1#, 1#, 1#, 0#
    ' Create infill block
    dblPnt(0) = 0#
    blkDefStart.InsertBlock dblPnt, CreateBlock(dblSpacerProj + dblSpacerGap, dblBlockThick, blnBlockHatch, "block", "blockinfill").Name, 1#, 1#, 1#, 0#
    ' Create DPC Lines
    varP1 = dblPnt
    varP1(1) = dblBlockThick + dblLinear5
    varP2 = varP1
    varP2(0) = varP2(0) + dblSpacerProj
    Set line = blkDefStart.AddLine(varP1, varP2)
    AecDtlApplication.Recipe.SetEntityProperties "dpc", line
    varP1 = varP2
    varP1(0) = varP1(0) + dblLinear5
    varP1(1) = varP1(1) + dblLinear5
    Set line = blkDefStart.AddLine(varP2, varP1)
    AecDtlApplication.Recipe.SetEntityProperties "dpc", line
    varP2 = varP1
    varP2(0) = dblOffset + dblSpacerProj + dblSpacerGap
    Set line = blkDefStart.AddLine(varP1, varP2)
    AecDtlApplication.Recipe.SetEntityProperties "dpc", line
    varP2(1) = varP2(1) - dblLinear5
    varP1 = varP2
    varP1(0) = dblSpacerProj + dblLinear5
    Set line = blkDefStart.AddLine(varP1, varP2)
    AecDtlApplication.Recipe.SetEntityProperties "dpc", line
    ' Create Insulation
    varP1(0) = dblSpacerProj
    varP1(1) = dblBlockThick + dblLinear10
    blkDefStart.InsertBlock varP1, CreateInsulation((dblSpacerGap + dblOffset), dblInsThick - dblLinear10, "insulation", "", False, False).Name, 1#, 1#, 1#, -Pi * 0.5
    ' Create Timber floor
    varP1(1) = varP1(1) + dblInsThick - dblLinear10
    blkDefStart.InsertBlock varP1, CreateBlock((dblSpacerGap + dblOffset), dblFloorThick, False, "floor", "", True, True, False, True).Name, 1#, 1#, 1#, 0#
    
    ' Create Intermediate Block
    ' Create Beam
    dblPnt(0) = dblOffset
    blkDefNext.InsertBlock dblPnt, CreateBeamSection(intBeamType, dblBlockThick).Name, -1#, 1#, 1#, 0#
    dblPnt(0) = dblOffset + dblBlockSize
    blkDefNext.InsertBlock dblPnt, CreateBeamSection(intBeamType, dblBlockThick).Name, 1#, 1#, 1#, 0#
    ' Create infill block
    dblPnt(0) = dblOffset
    blkDefNext.InsertBlock dblPnt, CreateBlock(dblBlockSize, dblBlockThick, blnBlockHatch, "block", "blockinfill").Name, 1#, 1#, 1#, 0#
    ' Create DPC Lines
    dblPnt(0) = 0#
    varP1 = dblPnt
    varP1(0) = 0#
    varP1(1) = dblBlockThick + dblLinear5
    varP2 = varP1
    varP2(0) = dblBlockSize + dblOffset * 2#
    Set line = blkDefNext.AddLine(varP1, varP2)
    AecDtlApplication.Recipe.SetEntityProperties "dpc", line
    ' Create Insulation
    varP1(0) = 0
    varP1(1) = dblBlockThick + dblLinear10
    blkDefNext.InsertBlock varP1, CreateInsulation(dblBlockSize + dblOffset * 2#, dblInsThick - dblLinear10, "insulation", "", False, False).Name, 1#, 1#, 1#, -Pi * 0.5
    ' Create Timber floor
    varP1(1) = varP1(1) + dblInsThick - dblLinear10
    blkDefNext.InsertBlock varP1, CreateBlock(dblBlockSize + dblOffset * 2#, dblFloorThick, False, "floor", "", False, True, False, True).Name, 1#, 1#, 1#, 0#

    ' Create End Block
    ' Create Beam
    dblPnt(0) = dblOffset
    blkDefEnd.InsertBlock dblPnt, CreateBeamSection(intBeamType, dblBlockThick).Name, -1#, 1#, 1#, 0#
    ' Create infill block
    blkDefEnd.InsertBlock dblPnt, CreateBlock(dblBlockSize, dblBlockThick, blnBlockHatch, "block", "blockinfill").Name, 1#, 1#, 1#, 0#
    ' Create DPC Lines
    dblPnt(0) = 0#
    varP1 = dblPnt
    varP1(0) = 0#
    varP1(1) = dblBlockThick + dblLinear5
    varP2 = varP1
    varP2(0) = dblBlockSize + dblOffset
    Set line = blkDefEnd.AddLine(varP1, varP2)
    AecDtlApplication.Recipe.SetEntityProperties "dpc", line
    ' Create Insulation
    varP1(0) = 0
    varP1(1) = dblBlockThick + dblLinear10
    blkDefEnd.InsertBlock varP1, CreateInsulation(dblBlockSize + dblOffset, dblInsThick - dblLinear10, "insulation", "", False, False).Name, 1#, 1#, 1#, -Pi * 0.5
    ' Create Timber floor
    varP1(1) = varP1(1) + dblInsThick - dblLinear10
    blkDefEnd.InsertBlock varP1, CreateBlock(dblBlockSize + dblOffset, dblFloorThick, False, "floor", "", False, True, False, True).Name, 1#, 1#, 1#, 0#
    
    ' start the jig
    Dim status As AecDtlPromptStatus
    status = AecDtlApplication.jig.BookendsBlock(blkDefStart, blkDefEnd, blkDefNext)

    ' return the status
    AecDtlApplication.Recipe.ReturnStatus = status

End Sub
Private Function CreateBeamSection(ByVal intType As Integer, ByVal dblBlockThick) As AcadBlock

    Dim dblPnt(0 To 2) As Double
    Dim line As AcadPolyline
    Dim dblPnts(0 To 17) As Double
    Dim lngI As Long
    Dim dblFactor As Double

    Set CreateBeamSection = ThisDrawing.Blocks.Add(dblPnt, "*U")
    
    dblFactor = AecDtlApplication.Recipe.GetDataValueDoubleUnitDep("Values", "Factor")
    
    If intType = 0 Then
    
        dblPnts(0) = 40.5: dblPnts(1) = -50#: dblPnts(2) = 0#
        dblPnts(3) = -23#: dblPnts(4) = -50#: dblPnts(5) = 0#
        dblPnts(6) = -23#: dblPnts(7) = 0#: dblPnts(8) = 0#
        dblPnts(9) = 0#: dblPnts(10) = 0#: dblPnts(11) = 0#
        dblPnts(12) = 4#: dblPnts(13) = dblBlockThick / dblFactor: dblPnts(14) = 0#
        dblPnts(15) = 40.5: dblPnts(16) = dblBlockThick / dblFactor: dblPnts(17) = 0#
        
    Else
    
        dblPnts(0) = 49#: dblPnts(1) = -125#: dblPnts(2) = 0#
        dblPnts(3) = -28.5: dblPnts(4) = -125#: dblPnts(5) = 0#
        dblPnts(6) = -23#: dblPnts(7) = 0#: dblPnts(8) = 0#
        dblPnts(9) = 0#: dblPnts(10) = 0#: dblPnts(11) = 0#
        dblPnts(12) = 4#: dblPnts(13) = dblBlockThick / dblFactor: dblPnts(14) = 0#
        dblPnts(15) = 49#: dblPnts(16) = dblBlockThick / dblFactor: dblPnts(17) = 0#
    
    End If
    
    For lngI = 0 To 17
        dblPnts(lngI) = dblPnts(lngI) * dblFactor
    Next lngI
    
    Set line = CreateBeamSection.AddPolyline(dblPnts)
    AecDtlApplication.Recipe.SetEntityProperties "beams", line

End Function
Private Function CreateInsulation(ByVal dblLength As Double, ByVal dblWidth As Double, ByVal strInsProps As String, ByVal strLineProps As String, ByVal blnLeftLine As Boolean, ByVal blnRightLine As Boolean) As AcadBlock

    Dim dblPnt(0 To 2) As Double
    Dim line As AcadLine
    Dim arc As AcadArc
    Dim dblStep As Double
    Dim dblRad As Double
    Dim dblPos As Double
    Dim intCount As Integer
    Dim lngI As Long
    Dim dblAng As Double
    Dim dblAng1 As Double
    Dim varP1 As Variant
    Dim varP2 As Variant
    Dim varP3 As Variant
    Dim varP4 As Variant
    Dim varP5 As Variant
    Dim varP6 As Variant
    Dim dblX As Double
    
    Set CreateInsulation = ThisDrawing.Blocks.Add(dblPnt, "*U")
    
    dblStep = dblWidth * 0.33333333
    intCount = CInt(dblLength / dblStep)
    
    If intCount < 1 Then
        Exit Function
    End If
    
    dblStep = dblLength / intCount
    dblRad = dblWidth * 0.15
    
    dblPnt(0) = 0#: dblPnt(1) = 0#: dblPnt(2) = 0#
    varP1 = dblPnt: varP2 = dblPnt
    
    varP1(0) = -dblRad
    varP2(0) = -dblWidth + dblRad
    varP2(1) = dblStep * 0.5
    
    dblX = CDLDist(varP1, varP2) * (dblRad / (dblRad + dblRad))
    dblAng = CDLAngle(varP1, varP2)
    dblAng1 = (CDLArcCos(dblRad / dblX) * -1) + dblAng
    varP3 = CDLPolar(varP1, dblAng1, dblRad)
    varP4 = CDLPolar(varP2, dblAng1 + Pi, dblRad)
    
    varP1 = varP2
    varP2(0) = -dblRad
    varP2(1) = dblStep
    
    dblX = CDLDist(varP1, varP2) * (dblRad / (dblRad + dblRad))
    dblAng = CDLAngle(varP1, varP2)
    dblAng1 = (CDLArcCos(dblRad / dblX)) + dblAng
    varP5 = CDLPolar(varP1, dblAng1, dblRad)
    varP6 = CDLPolar(varP2, dblAng1 + Pi, dblRad)
    
    dblPos = 0#
    varP1 = dblPnt
    varP1(0) = -dblRad
    varP2 = dblPnt
    varP2(0) = -dblWidth + dblRad
    varP2(1) = dblStep * 0.5
    dblAng = CDLAngle(varP1, varP3)
    dblAng1 = CDLAngle(varP2, varP4)
    For lngI = 1 To intCount
        Set line = CreateInsulation.AddLine(varP3, varP4)
        AecDtlApplication.Recipe.SetEntityProperties strInsProps, line
        Set line = CreateInsulation.AddLine(varP5, varP6)
        AecDtlApplication.Recipe.SetEntityProperties strInsProps, line
        If lngI = 1 Then
            Set arc = CreateInsulation.AddArc(varP1, dblRad, 0#, dblAng)
        Else
            Set arc = CreateInsulation.AddArc(varP1, dblRad, -dblAng, dblAng)
        End If
        AecDtlApplication.Recipe.SetEntityProperties strInsProps, arc
        Set arc = CreateInsulation.AddArc(varP2, dblRad, -dblAng1, dblAng1)
        AecDtlApplication.Recipe.SetEntityProperties strInsProps, arc
        varP1(1) = varP1(1) + dblStep
        varP2(1) = varP2(1) + dblStep
        varP3(1) = varP3(1) + dblStep
        varP4(1) = varP4(1) + dblStep
        varP5(1) = varP5(1) + dblStep
        varP6(1) = varP6(1) + dblStep
    Next lngI
    Set arc = CreateInsulation.AddArc(varP1, dblRad, -dblAng, 0#)
    AecDtlApplication.Recipe.SetEntityProperties strInsProps, arc
    
    If blnLeftLine Then
        varP1 = dblPnt
        varP1(0) = -dblWidth
        varP2 = varP1
        varP2(1) = dblLength
        Set line = CreateInsulation.AddLine(varP1, varP2)
        AecDtlApplication.Recipe.SetEntityProperties strLineProps, line
    End If
    
    If blnRightLine Then
        varP1 = dblPnt
        varP2 = varP1
        varP2(1) = dblLength
        Set line = CreateInsulation.AddLine(varP1, varP2)
        AecDtlApplication.Recipe.SetEntityProperties strLineProps, line
    End If
    
End Function
Private Function CreateHardcore(ByVal dblLength As Double, ByVal dblWidth As Double, ByVal strHardcoreProps As String, ByVal strLineProps As String, ByVal blnLeftLine As Boolean, ByVal blnRightLine As Boolean) As AcadBlock

    Dim dblPnt(0 To 2) As Double
    Dim line As AcadLine
    Dim dblStep As Double
    Dim intCount As Integer
    Dim lngI As Long
    Dim varP1 As Variant
    Dim varP2 As Variant
    Dim varP3 As Variant
    
    Set CreateHardcore = ThisDrawing.Blocks.Add(dblPnt, "*U")
    
    dblStep = dblWidth
    intCount = CInt(dblLength / dblStep)
    dblStep = dblLength / intCount
    
    dblPnt(0) = 0#: dblPnt(1) = 0#: dblPnt(2) = 0#
    varP1 = dblPnt: varP2 = dblPnt: varP3 = dblPnt
    
    varP1(0) = 0#
    varP2(0) = -dblWidth
    varP2(1) = dblStep * 0.5
    varP3(1) = dblStep
    
    For lngI = 1 To intCount
        Set line = CreateHardcore.AddLine(varP1, varP2)
        AecDtlApplication.Recipe.SetEntityProperties strHardcoreProps, line
        Set line = CreateHardcore.AddLine(varP2, varP3)
        AecDtlApplication.Recipe.SetEntityProperties strHardcoreProps, line
        varP1(1) = varP1(1) + dblStep
        varP2(1) = varP2(1) + dblStep
        varP3(1) = varP3(1) + dblStep
    Next lngI
    
    If blnLeftLine Then
        varP1 = dblPnt
        varP1(0) = -dblWidth
        varP2 = varP1
        varP2(1) = dblLength
        Set line = CreateHardcore.AddLine(varP1, varP2)
        AecDtlApplication.Recipe.SetEntityProperties strLineProps, line
    End If
    
    If blnRightLine Then
        varP1 = dblPnt
        varP2 = varP1
        varP2(1) = dblLength
        Set line = CreateHardcore.AddLine(varP1, varP2)
        AecDtlApplication.Recipe.SetEntityProperties strLineProps, line
    End If
    
End Function
Private Function CreateBlock(ByVal dblWidth As Double, ByVal dblHeight As Double, ByVal blnHatch As Boolean, ByVal strEntityProps As String, ByVal strHatchProps As String, Optional ByVal blnLeftLine As Boolean = True, Optional ByVal blnTopLine As Boolean = True, Optional ByVal blnRightLine As Boolean = True, Optional ByVal blnBottomLine As Boolean = True) As AcadBlock

    Dim dblPnt(0 To 2) As Double
    Dim line As AcadPolyline
    Dim bline As AcadLine
    Dim objHatch As AcadHatch
    Dim outerLoop(0) As AcadEntity
    Dim varP1 As Variant
    Dim varP2 As Variant
    Dim varP3 As Variant
    Dim varP4 As Variant
    
    dblPnt(0) = 0#
    dblPnt(1) = 0#
    dblPnt(2) = 0#
    
    Set CreateBlock = ThisDrawing.Blocks.Add(dblPnt, "*U")
    
    Dim dblPnts(0 To 11) As Double
    
    dblPnts(0) = 0#: dblPnts(1) = 0#: dblPnts(2) = 0#
    dblPnts(3) = dblWidth: dblPnts(4) = 0#: dblPnts(5) = 0#
    dblPnts(6) = dblWidth: dblPnts(7) = dblHeight: dblPnts(8) = 0#
    dblPnts(9) = 0#: dblPnts(10) = dblHeight: dblPnts(11) = 0#

    Set line = CreateBlock.AddPolyline(dblPnts)
    line.Closed = True

    If blnHatch Then
        
        Set objHatch = CreateBlock.AddHatch(0, "ANSI31", True)
        
        AecDtlApplication.Recipe.SetHatchProperties strHatchProps, objHatch
        AecDtlApplication.Recipe.SetEntityProperties strHatchProps, objHatch
        
        Set outerLoop(0) = line
        objHatch.AppendOuterLoop outerLoop
        objHatch.Evaluate
    
    End If
    
    If blnLeftLine And blnTopLine And blnRightLine And blnBottomLine Then
        
        AecDtlApplication.Recipe.SetEntityProperties strEntityProps, line
    
    Else
    
        line.Delete
        
        varP1 = dblPnt
        varP2 = dblPnt
        varP2(1) = dblHeight
        varP3 = varP1
        varP3(0) = dblWidth
        varP4 = varP2
        varP4(0) = dblWidth
        
        If blnLeftLine Then
            Set bline = CreateBlock.AddLine(varP1, varP2)
            AecDtlApplication.Recipe.SetEntityProperties strEntityProps, bline
        End If
        If blnTopLine Then
            Set bline = CreateBlock.AddLine(varP2, varP4)
            AecDtlApplication.Recipe.SetEntityProperties strEntityProps, bline
        End If
        If blnRightLine Then
            Set bline = CreateBlock.AddLine(varP3, varP4)
            AecDtlApplication.Recipe.SetEntityProperties strEntityProps, bline
        End If
        If blnBottomLine Then
            Set bline = CreateBlock.AddLine(varP1, varP3)
            AecDtlApplication.Recipe.SetEntityProperties strEntityProps, bline
        End If
        
    End If

End Function
Private Function CreateTimberSection(ByVal dblWidth As Double, ByVal dblHeight As Double, ByVal strEntityProps As String) As AcadBlock

    Dim dblPnt(0 To 2) As Double
    Dim line As AcadLine
    Dim varP1 As Variant
    Dim varP2 As Variant
    Dim varP3 As Variant
    Dim varP4 As Variant
    
    dblPnt(0) = 0#
    dblPnt(1) = 0#
    dblPnt(2) = 0#
    
    Set CreateTimberSection = ThisDrawing.Blocks.Add(dblPnt, "*U")
    
    varP1 = dblPnt
    varP2 = dblPnt
    varP2(0) = dblWidth
    varP3 = varP2
    varP2(1) = -dblHeight
    varP4 = varP1
    varP4(1) = -dblHeight
    
    Set line = CreateTimberSection.AddLine(varP1, varP2)
    AecDtlApplication.Recipe.SetEntityProperties strEntityProps, line
    Set line = CreateTimberSection.AddLine(varP2, varP3)
    AecDtlApplication.Recipe.SetEntityProperties strEntityProps, line
    Set line = CreateTimberSection.AddLine(varP3, varP4)
    AecDtlApplication.Recipe.SetEntityProperties strEntityProps, line
    Set line = CreateTimberSection.AddLine(varP4, varP1)
    AecDtlApplication.Recipe.SetEntityProperties strEntityProps, line
    Set line = CreateTimberSection.AddLine(varP1, varP3)
    AecDtlApplication.Recipe.SetEntityProperties strEntityProps, line
    Set line = CreateTimberSection.AddLine(varP2, varP4)
    AecDtlApplication.Recipe.SetEntityProperties strEntityProps, line

End Function
Private Function CreateMortar(ByVal dblWidth As Double, ByVal dblHeight As Double) As AcadBlock

    Dim dblPnt(0 To 2) As Double
    Dim line As AcadLine
    Dim arc As AcadArc
    Dim varP1 As Variant
    Dim varP2 As Variant
    Dim varP3 As Variant
    Dim varP4 As Variant
    Dim varP5 As Variant
    Dim varP6 As Variant
    Dim strLeft As String
    Dim strRight As String
    Dim blnHatch As Boolean
    Dim pline As AcadPolyline
    Dim objHatch As AcadHatch
    Dim outerLoop(0) As AcadEntity
    Dim intCount As Integer
    Dim intPos As Integer
    Dim blnShow As Boolean
    
    dblPnt(0) = 0#
    dblPnt(1) = 0#
    dblPnt(2) = 0#
    
    Set CreateMortar = ThisDrawing.Blocks.Add(dblPnt, "*U")
    
    strLeft = AecDtlApplication.Palette.GetPropertyValueStr("leftJointType")
    strRight = AecDtlApplication.Palette.GetPropertyValueStr("rightJointType")
    blnHatch = AecDtlApplication.Palette.GetPropertyValueBool("doMortarHatch")
    blnShow = AecDtlApplication.Palette.GetPropertyValueBool("showMortar")
    
    If blnShow Then
    
        varP1 = dblPnt
        varP2 = dblPnt
        varP2(0) = dblWidth
        varP3 = varP2
        varP2(1) = dblHeight
        varP4 = varP1
        varP4(1) = dblHeight
        
        intCount = 4
        
        Select Case UCase(strLeft)
            Case "FLUSH"
                Set line = CreateMortar.AddLine(varP1, varP4)
                AecDtlApplication.Recipe.SetEntityProperties "boundary", line
            Case "RODDED"
                varP5 = varP1
                varP5(1) = varP5(1) + dblHeight * 0.5
                Set arc = CreateMortar.AddArc(varP5, dblHeight * 0.5, -Pi * 0.5, Pi * 0.5)
                AecDtlApplication.Recipe.SetEntityProperties "boundary", arc
            Case "RAKED"
                varP1(0) = varP1(0) + dblHeight
                varP4(0) = varP4(0) + dblHeight
                Set line = CreateMortar.AddLine(varP1, varP4)
                AecDtlApplication.Recipe.SetEntityProperties "boundary", line
            Case "VSHAPED"
                varP5 = varP1
                varP5(0) = varP5(0) + dblHeight * 0.5
                varP5(1) = varP5(1) + dblHeight * 0.5
                Set line = CreateMortar.AddLine(varP1, varP5)
                AecDtlApplication.Recipe.SetEntityProperties "boundary", line
                Set line = CreateMortar.AddLine(varP5, varP4)
                AecDtlApplication.Recipe.SetEntityProperties "boundary", line
                intCount = intCount + 1
        End Select
        
        Select Case UCase(strRight)
            Case "FLUSH"
                Set line = CreateMortar.AddLine(varP2, varP3)
                AecDtlApplication.Recipe.SetEntityProperties "boundary", line
            Case "RODDED"
                varP6 = varP3
                varP6(1) = varP6(1) + dblHeight * 0.5
                Set arc = CreateMortar.AddArc(varP6, dblHeight * 0.5, Pi * 0.5, -Pi * 0.5)
                AecDtlApplication.Recipe.SetEntityProperties "boundary", arc
            Case "RAKED"
                varP2(0) = varP2(0) - dblHeight
                varP3(0) = varP3(0) - dblHeight
                Set line = CreateMortar.AddLine(varP2, varP3)
                AecDtlApplication.Recipe.SetEntityProperties "boundary", line
            Case "VSHAPED"
                varP6 = varP3
                varP6(0) = varP6(0) - dblHeight * 0.5
                varP6(1) = varP6(1) + dblHeight * 0.5
                Set line = CreateMortar.AddLine(varP2, varP6)
                AecDtlApplication.Recipe.SetEntityProperties "boundary", line
                Set line = CreateMortar.AddLine(varP6, varP3)
                AecDtlApplication.Recipe.SetEntityProperties "boundary", line
                intCount = intCount + 1
        End Select
    
        If blnHatch Then
        
            ReDim dblPnts(0 To (intCount * 3) - 1) As Double
            
            intPos = 0
            dblPnts(intPos) = varP1(0): dblPnts(intPos + 1) = varP1(1): dblPnts(intPos + 2) = 0#
            intPos = intPos + 3
            If UCase(strLeft) = "VSHAPED" Then
                dblPnts(intPos) = varP5(0): dblPnts(intPos + 1) = varP5(1): dblPnts(intPos + 2) = 0#
                intPos = intPos + 3
            End If
            dblPnts(intPos) = varP4(0): dblPnts(intPos + 1) = varP4(1): dblPnts(intPos + 2) = 0#
            intPos = intPos + 3
            dblPnts(intPos) = varP2(0): dblPnts(intPos + 1) = varP2(1): dblPnts(intPos + 2) = 0#
            intPos = intPos + 3
            If UCase(strRight) = "VSHAPED" Then
                dblPnts(intPos) = varP6(0): dblPnts(intPos + 1) = varP6(1): dblPnts(intPos + 2) = 0#
                intPos = intPos + 3
            End If
            dblPnts(intPos) = varP3(0): dblPnts(intPos + 1) = varP3(1): dblPnts(intPos + 2) = 0#
        
            Set pline = CreateMortar.AddPolyline(dblPnts)
            
            If UCase(strLeft) = "RODDED" Then
                pline.SetBulge 0, 1#
            End If
            If UCase(strRight) = "RODDED" Then
                If UCase(strLeft) = "VSHAPED" Then
                    pline.SetBulge 3, 1#
                Else
                    pline.SetBulge 2, 1#
                End If
            End If
            
            pline.Closed = True
    
            Set objHatch = CreateMortar.AddHatch(0, "ANSI31", True)
            
            AecDtlApplication.Recipe.SetHatchProperties "mortarinfill", objHatch
            AecDtlApplication.Recipe.SetEntityProperties "mortarinfill", objHatch
            
            Set outerLoop(0) = pline
            objHatch.AppendOuterLoop outerLoop
            objHatch.Evaluate
    
            pline.Delete
        
        End If
        
    End If

End Function
Public Sub AecDtlRcpSteelPFChannelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblOrgX As Double
    Dim dblOrgY As Double
    
    ' get the db values
    Dim depth As Double
    Dim tw As Double
    Dim bf As Double
    Dim tf As Double
    Dim ri As Double
    Dim xbar As Double
    
    depth = AecDtlApplication.Database.GetFieldValueDoubleUnitDep("DEPTH")
    tw = AecDtlApplication.Database.GetFieldValueDoubleUnitDep("TW")
    bf = AecDtlApplication.Database.GetFieldValueDoubleUnitDep("BF")
    tf = AecDtlApplication.Database.GetFieldValueDoubleUnitDep("TF")
    ri = AecDtlApplication.Database.GetFieldValueDoubleUnitDep("RI")
    xbar = AecDtlApplication.Database.GetFieldValueDoubleUnitDep("XBAR")
    
    ' get the palette values
    Dim insert As String
    Dim hatch As Boolean
    insert = AecDtlApplication.Palette.GetPropertyValueStr("insertMode")
    hatch = AecDtlApplication.Palette.GetPropertyValueBool("doHatch")
    
    If insert = "top" Then
        dblOrgX = 0#: dblOrgY = -depth
    Else
        dblOrgX = -xbar: dblOrgY = -depth / 2#
    End If
    
    Dim dblPnts(0 To 29) As Double
    
    dblPnts(0) = dblOrgX: dblPnts(1) = dblOrgY: dblPnts(2) = 0#
    dblPnts(3) = bf + dblOrgX: dblPnts(4) = dblOrgY: dblPnts(5) = 0#
    dblPnts(6) = bf + dblOrgX: dblPnts(7) = tf + dblOrgY: dblPnts(8) = 0#
    dblPnts(9) = tw + ri + dblOrgX: dblPnts(10) = tf + dblOrgY: dblPnts(11) = 0#
    dblPnts(12) = tw + dblOrgX: dblPnts(13) = tf + ri + dblOrgY: dblPnts(14) = 0#
    dblPnts(15) = tw + dblOrgX: dblPnts(16) = depth - tf - ri + dblOrgY: dblPnts(17) = 0#
    dblPnts(18) = tw + ri + dblOrgX: dblPnts(19) = depth - tf + dblOrgY: dblPnts(20) = 0#
    dblPnts(21) = bf + dblOrgX: dblPnts(22) = depth - tf + dblOrgY: dblPnts(23) = 0#
    dblPnts(24) = bf + dblOrgX: dblPnts(25) = depth + dblOrgY: dblPnts(26) = 0#
    dblPnts(27) = dblOrgX: dblPnts(28) = depth + dblOrgY: dblPnts(29) = 0#
    
    Dim line As AcadPolyline
    
    Set line = blkdef.AddPolyline(dblPnts)
    line.Closed = True
    
    line.SetBulge 3, -0.414213562373095
    line.SetBulge 5, -0.414213562373095
    
    Dim objHatch As AcadHatch
    Dim outerLoop(0 To 0) As AcadEntity
    If hatch Then
        Set objHatch = blkdef.AddHatch(0, "ANSI31", True)
        AecDtlApplication.Recipe.SetHatchProperties "infill", objHatch
        AecDtlApplication.Recipe.SetEntityProperties "infill", objHatch
        Set outerLoop(0) = line
        objHatch.AppendOuterLoop outerLoop
        objHatch.Evaluate
    End If

    ' start the jig
    Dim status As AecDtlPromptStatus
    status = AecDtlApplication.jig.StampBlock(blkdef)

    ' return the status
    AecDtlApplication.Recipe.ReturnStatus = status

End Sub
Public Sub AecDtlRcpSteelPFChannelPlan()

    Dim dblPnt(0 To 2) As Double
    Dim blkdef As AcadBlock
    dblPnt(0) = 0#
    dblPnt(1) = 0#
    dblPnt(2) = 0#
    Set blkdef = ThisDrawing.Blocks.Add(dblPnt, "*U")
    
    ' get the db values
    Dim tw As Double
    Dim bf As Double
    
    tw = AecDtlApplication.Database.GetFieldValueDoubleUnitDep("TW")
    bf = AecDtlApplication.Database.GetFieldValueDoubleUnitDep("BF")
    
    ' get the palette values
    Dim hideweb As Boolean
    hideweb = AecDtlApplication.Palette.GetPropertyValueBool("hideWeb")

    Dim objLine As AcadLine
    Dim dblPnt1(0 To 2) As Double
    Dim dblpnt2(0 To 2) As Double
    
    dblPnt1(0) = 0#: dblPnt1(1) = 0#: dblPnt1(2) = 0#
    dblpnt2(0) = 0#: dblpnt2(1) = -bf: dblpnt2(2) = 0#
    
    Set objLine = blkdef.AddLine(dblPnt1, dblpnt2)
    AecDtlApplication.Recipe.SetEntityProperties "boundary", objLine

    dblpnt2(0) = 1#: dblpnt2(1) = 0#: dblpnt2(2) = 0#
    Set objLine = blkdef.AddLine(dblPnt1, dblpnt2)
    AecDtlApplication.Recipe.SetEntityProperties "boundary", objLine
    
    dblPnt1(1) = -bf: dblpnt2(1) = -bf
    Set objLine = blkdef.AddLine(dblPnt1, dblpnt2)
    AecDtlApplication.Recipe.SetEntityProperties "boundary", objLine
    
    dblPnt1(1) = -tw: dblpnt2(1) = -tw
    Set objLine = blkdef.AddLine(dblPnt1, dblpnt2)
    If Not hideweb Then
        AecDtlApplication.Recipe.SetEntityProperties "boundary", objLine
    Else
        AecDtlApplication.Recipe.SetEntityProperties "hidden", objLine
    End If

    dblPnt1(0) = 1#: dblPnt1(1) = 0#: dblPnt1(2) = 0#
    dblpnt2(0) = 1#: dblpnt2(1) = -bf: dblpnt2(2) = 0#
    
    Set objLine = blkdef.AddLine(dblPnt1, dblpnt2)
    AecDtlApplication.Recipe.SetEntityProperties "boundary", objLine
    
    ' start the jig
    Dim status As AecDtlPromptStatus
    status = AecDtlApplication.jig.StretchBlock(blkdef)

    ' return the status
    AecDtlApplication.Recipe.ReturnStatus = status

End Sub
Public Sub AecDtlRcpSteelPFChannelElev()

    Dim dblPnt(0 To 2) As Double
    Dim blkdef As AcadBlock
    dblPnt(0) = 0#
    dblPnt(1) = 0#
    dblPnt(2) = 0#
    Set blkdef = ThisDrawing.Blocks.Add(dblPnt, "*U")
    
    ' get the db values
    Dim depth As Double
    Dim tf As Double
    
    depth = AecDtlApplication.Database.GetFieldValueDoubleUnitDep("DEPTH")
    tf = AecDtlApplication.Database.GetFieldValueDoubleUnitDep("TF")
    
    ' get the palette values
    Dim hideflanges As Boolean
    hideflanges = AecDtlApplication.Palette.GetPropertyValueBool("hideFlanges")

    Dim objLine As AcadLine
    Dim dblPnt1(0 To 2) As Double
    Dim dblpnt2(0 To 2) As Double
    
    dblPnt1(0) = 0#: dblPnt1(1) = 0#: dblPnt1(2) = 0#
    dblpnt2(0) = 0#: dblpnt2(1) = -depth: dblpnt2(2) = 0#
    
    Set objLine = blkdef.AddLine(dblPnt1, dblpnt2)
    AecDtlApplication.Recipe.SetEntityProperties "boundary", objLine

    dblpnt2(0) = 1#: dblpnt2(1) = 0#: dblpnt2(2) = 0#
    Set objLine = blkdef.AddLine(dblPnt1, dblpnt2)
    AecDtlApplication.Recipe.SetEntityProperties "boundary", objLine
    
    dblPnt1(1) = -depth: dblpnt2(1) = -depth
    Set objLine = blkdef.AddLine(dblPnt1, dblpnt2)
    AecDtlApplication.Recipe.SetEntityProperties "boundary", objLine
    
    dblPnt1(1) = -tf: dblpnt2(1) = -tf
    Set objLine = blkdef.AddLine(dblPnt1, dblpnt2)
    If Not hideflanges Then
        AecDtlApplication.Recipe.SetEntityProperties "boundary", objLine
    Else
        AecDtlApplication.Recipe.SetEntityProperties "hidden", objLine
    End If

    dblPnt1(1) = -depth + tf: dblpnt2(1) = -depth + tf
    Set objLine = blkdef.AddLine(dblPnt1, dblpnt2)
    If Not hideflanges Then
        AecDtlApplication.Recipe.SetEntityProperties "boundary", objLine
    Else
        AecDtlApplication.Recipe.SetEntityProperties "hidden", objLine
    End If

    dblPnt1(0) = 1#: dblPnt1(1) = 0#: dblPnt1(2) = 0#
    dblpnt2(0) = 1#: dblpnt2(1) = -depth: dblpnt2(2) = 0#
    
    Set objLine = blkdef.AddLine(dblPnt1, dblpnt2)
    AecDtlApplication.Recipe.SetEntityProperties "boundary", objLine
    
    ' start the jig
    Dim status As AecDtlPromptStatus
    status = AecDtlApplication.jig.StretchBlock(blkdef)

    ' return the status
    AecDtlApplication.Recipe.ReturnStatus = status

End Sub
Public Sub AecDtlRcpSteelCGLintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim lngI As Long
    Dim dblAng1 As Double
    Dim dblOrgX As Double
    Dim dblOrgY As Double
    Dim varEnt As Variant
    Dim varPnt1 As Variant
    Dim varPnt2 As Variant
    Dim varPnt3 As Variant
    Dim varPnt4 As Variant
    
    ' get the db values
    Dim cat_a As Double
    Dim cat_b As Double
    Dim cat_c As Double
    Dim cat_d As Double
    Dim cat_e As Double
    Dim cat_f As Double
    Dim cat_g As Double
    Dim cat_h As Double
    
    cat_h = AecDtlApplication.Database.GetFieldValueDoubleUnitDep("HEIGHT")
    cat_a = AecDtlApplication.Database.GetFieldValueDoubleUnitDep("CAT_A")
    cat_b = AecDtlApplication.Database.GetFieldValueDoubleUnitDep("CAT_B")
    cat_c = AecDtlApplication.Database.GetFieldValueDoubleUnitDep("CAT_C")
    cat_d = AecDtlApplication.Database.GetFieldValueDoubleUnitDep("CAT_D")
    cat_e = AecDtlApplication.Database.GetFieldValueDoubleUnitDep("CAT_E")
    cat_f = AecDtlApplication.Database.GetFieldValueDoubleUnitDep("CAT_F")
    cat_g = AecDtlApplication.Database.GetFieldValueDoubleUnitDep("CAT_G")
    
    If cat_d + cat_e = 0 Then
        cat_d = cat_d + 1#
        cat_c = cat_c - 1#
    End If
    
    ' get the palette values
    Dim hatch As Boolean
    hatch = AecDtlApplication.Palette.GetPropertyValueBool("doHatch")
    
    dblOrgX = -(cat_d + cat_c): dblOrgY = -(cat_e + (cat_g * 0.75))
    
    varPnt1 = Array(CDbl(0#), CDbl(0#), CDbl(0#)): varPnt2 = varPnt1
    
    varPnt1(0) = dblOrgX + cat_d + cat_c
    varPnt1(1) = dblOrgY + cat_e + cat_f
    varPnt2(0) = dblOrgX + cat_d + cat_c + cat_b - (cat_g * 1.5)
    varPnt2(1) = dblOrgY + cat_e + cat_h - (cat_g * 1.5)
    
    varPnt3 = CDLPolar(varPnt1, CDLArcSin((cat_g * 1.5) / CDLDist(varPnt1, varPnt2)) + CDLAngle(varPnt1, varPnt2), 10#)
    CDLPerp varPnt1, varPnt3, varPnt2, varPnt4
    
    dblAng1 = Tan(CDLAngle(varPnt2, varPnt4) * 0.25)
    
    Dim dblPnts(0 To 32) As Double
    
    dblPnts(0) = dblOrgX: dblPnts(1) = dblOrgY: dblPnts(2) = 0#
    dblPnts(3) = dblOrgX + cat_d: dblPnts(4) = dblOrgY + cat_e: dblPnts(5) = 0#
    dblPnts(6) = dblOrgX + cat_d + cat_c - (cat_g * 0.75): dblPnts(7) = dblOrgY + cat_e: dblPnts(8) = 0#
    dblPnts(9) = dblOrgX + cat_d + cat_c: dblPnts(10) = dblOrgY + cat_e + (cat_g * 0.75): dblPnts(11) = 0#
    dblPnts(12) = dblOrgX + cat_d + cat_c: dblPnts(13) = dblOrgY + cat_e + cat_f: dblPnts(14) = 0#
    dblPnts(15) = dblOrgX + cat_d + cat_c: dblPnts(16) = dblOrgY + cat_e + cat_f: dblPnts(17) = 0#
    dblPnts(18) = varPnt4(0): dblPnts(19) = varPnt4(1): dblPnts(20) = 0#
    dblPnts(21) = dblOrgX + cat_d + cat_c + cat_b: dblPnts(22) = dblOrgY + cat_e + cat_h - (cat_g * 1.5): dblPnts(23) = 0#
    dblPnts(24) = dblOrgX + cat_d + cat_c + cat_b: dblPnts(25) = dblOrgY + cat_e + (cat_g * 0.75): dblPnts(26) = 0#
    dblPnts(27) = dblOrgX + cat_d + cat_c + cat_b + (cat_g * 0.75): dblPnts(28) = dblOrgY + cat_e: dblPnts(29) = 0#
    dblPnts(30) = dblOrgX + cat_d + cat_c + cat_b + cat_a: dblPnts(31) = dblOrgY + cat_e: dblPnts(32) = 0#
    
    Dim line1 As AcadPolyline
    Dim line2 As AcadPolyline
    
    Set line1 = blkdef.AddPolyline(dblPnts)
    
    varEnt = line1.Offset(cat_g * 1.5)
    varPnt1 = varEnt(0).Coordinate(4)
    varEnt(0).Delete
    line1.Delete
    
    varPnt2 = varPnt1
    varPnt2(0) = varPnt2(0) - (cat_g * 1.5)
    dblPnts(12) = varPnt2(0): dblPnts(13) = varPnt2(1)
    
    varPnt3 = varPnt1: varPnt4 = varPnt1
    varPnt3(0) = dblPnts(15): varPnt3(1) = dblPnts(16): varPnt3(2) = dblPnts(17)
    varPnt4(0) = dblPnts(18): varPnt4(1) = dblPnts(19): varPnt4(2) = dblPnts(20)
    
    CDLPerp varPnt3, varPnt4, varPnt1, varPnt2
    dblPnts(15) = varPnt2(0): dblPnts(16) = varPnt2(1)

    Set line1 = blkdef.AddPolyline(dblPnts)

    line1.SetBulge 2, 0.414213562373095
    line1.SetBulge 4, -Tan(((180 * DegToRad) - CDLAngle(varPnt1, varPnt2)) * 0.25)
    line1.SetBulge 6, -dblAng1
    line1.SetBulge 8, 0.414213562373095

    varEnt = line1.Offset(cat_g)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    If hatch Then
        ReDim dblPnts2(0 To UBound(line2.Coordinates) - 9) As Double
    
        For lngI = 6 To (UBound(line2.Coordinates) - 3)
            dblPnts2(lngI - 6) = line2.Coordinates(lngI)
        Next lngI
    
        Set line1 = blkdef.AddPolyline(dblPnts2)
        line1.Closed = True
    
        line1.SetBulge 0, 0.414213562373095
        line1.SetBulge 2, -Tan(((180 * DegToRad) - CDLAngle(varPnt1, varPnt2)) * 0.25)
        line1.SetBulge 4, -dblAng1
        line1.SetBulge 6, 0.414213562373095
    
        Dim objHatch As AcadHatch
        Dim outerLoop(0 To 0) As AcadEntity
        Set objHatch = blkdef.AddHatch(0, "ANSI31", True)
        AecDtlApplication.Recipe.SetHatchProperties "infill", objHatch
        AecDtlApplication.Recipe.SetEntityProperties "infill", objHatch
        Set outerLoop(0) = line1
        objHatch.AppendOuterLoop outerLoop
        objHatch.Evaluate
    
        line1.Delete
    End If

    ' start the jig
    Dim status As AecDtlPromptStatus
    status = AecDtlApplication.jig.StampBlock(blkdef)

    ' return the status
    AecDtlApplication.Recipe.ReturnStatus = status

End Sub
Public Sub AecDtlRcpSteelCULintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim lngI As Long
    Dim dblAng1 As Double
    Dim dblAng2 As Double
    Dim dblAngl As Double
    Dim dblOrgX As Double
    Dim dblOrgY As Double
    Dim varEnt As Variant
    Dim varPnt1 As Variant
    Dim varPnt2 As Variant
    Dim varPnt3 As Variant
    Dim varPnt4 As Variant
    Dim varPnt5 As Variant
    Dim varPnt6 As Variant
    Dim dblR1 As Double
    Dim dblR2 As Double
    
    ' get the db values
    Dim cat_a As Double
    Dim cat_b As Double
    Dim cat_c As Double
    Dim cat_d As Double
    Dim cat_e As Double
    Dim cat_f As Double
    Dim cat_h As Double
    Dim cat_TopLen As Double
    Dim cat_TopLip As Double
    Dim cat_LeftBaseLen As Double
    Dim cat_RightBaseLen As Double
    Dim cat_BaseThick As Double
    
    cat_h = AecDtlApplication.Database.GetFieldValueDoubleUnitDep("HEIGHT")
    cat_a = AecDtlApplication.Database.GetFieldValueDoubleUnitDep("CAT_A")
    cat_b = AecDtlApplication.Database.GetFieldValueDoubleUnitDep("CAT_B")
    cat_c = AecDtlApplication.Database.GetFieldValueDoubleUnitDep("CAT_C")
    cat_d = AecDtlApplication.Database.GetFieldValueDoubleUnitDep("CAT_D")
    cat_e = AecDtlApplication.Database.GetFieldValueDoubleUnitDep("CAT_E")
    cat_f = AecDtlApplication.Database.GetFieldValueDoubleUnitDep("CAT_F")
    
    ' get the palette values
    Dim hatch As Boolean
    hatch = AecDtlApplication.Palette.GetPropertyValueBool("doHatch")
    
    cat_TopLen = AecDtlApplication.Recipe.GetDataValueDoubleUnitDep("boundary", "TopLength")
    cat_TopLip = AecDtlApplication.Recipe.GetDataValueDoubleUnitDep("boundary", "TopLip")
    cat_LeftBaseLen = AecDtlApplication.Recipe.GetDataValueDoubleUnitDep("boundary", "LeftBaseLen")
    cat_RightBaseLen = AecDtlApplication.Recipe.GetDataValueDoubleUnitDep("boundary", "RightBaseLen")
    cat_BaseThick = AecDtlApplication.Recipe.GetDataValueDoubleUnitDep("boundary", "BaseThick")
    
    dblOrgX = -(cat_d + cat_c): dblOrgY = -cat_e
    
    varPnt1 = Array(CDbl(dblOrgX + cat_d + cat_c), CDbl(dblOrgY + cat_e + (cat_f * 0.75)), CDbl(0#))
    varPnt2 = Array(CDbl(dblOrgX + cat_d + cat_c + cat_b), CDbl(dblOrgY + cat_e + cat_h - cat_BaseThick - (cat_f * 3.75)), CDbl(0#))
    
    dblR1 = cat_f * 0.75
    dblR2 = cat_f * 2.75
    dblAngl = CDLAngle(varPnt1, varPnt2)

    If CDLApproxEqual(dblR1 + dblR2, 0#, 0.0001) Then
        dblAng1 = (90# * DegToRad) + dblAngl
    Else
        dblAng1 = (CDLArcCos(dblR1 / (CDLDist(varPnt1, varPnt2) * (dblR1 / (dblR1 + dblR2)))) * -1#) + dblAngl
    End If

    varPnt3 = CDLPolar(varPnt1, dblAng1, dblR1)
    varPnt5 = CDLPolar(varPnt1, 270# * DegToRad, dblR1)
    varPnt4 = CDLPolar(varPnt2, dblAng1 + (180# * DegToRad), dblR2)
    varPnt6 = CDLPolar(varPnt2, 90# * DegToRad, dblR2)
    
    dblAng1 = Abs((270# * DegToRad) - CDLAngle(varPnt1, varPnt3))
    dblAng2 = CDLAngle(varPnt2, varPnt4) - (90# * DegToRad)
    
    varPnt1 = Array(CDbl(0#), CDbl(0#), CDbl(0#)): varPnt2 = varPnt1
    
    ReDim dblPnts(0 To 20) As Double
    
    dblPnts(0) = dblOrgX: dblPnts(1) = dblOrgY: dblPnts(2) = 0#
    dblPnts(3) = dblOrgX + cat_d: dblPnts(4) = dblOrgY + cat_e: dblPnts(5) = 0#
    
    dblPnts(6) = dblOrgX + cat_d + cat_c: dblPnts(7) = dblOrgY + cat_e: dblPnts(8) = 0#
    dblPnts(9) = varPnt3(0): dblPnts(10) = varPnt3(1): dblPnts(11) = 0#
    
    dblPnts(12) = varPnt4(0): dblPnts(13) = varPnt4(1): dblPnts(14) = 0#
    dblPnts(15) = dblOrgX + cat_d + cat_c + cat_b: dblPnts(16) = dblOrgY + cat_e + cat_h - cat_BaseThick - cat_f: dblPnts(17) = 0#
    
    dblPnts(18) = dblOrgX + cat_d + cat_c + cat_b - (cat_f * 0.75) + cat_TopLen - cat_TopLip: dblPnts(19) = dblOrgY + cat_e + cat_h - cat_BaseThick - cat_f: dblPnts(20) = 0#
    
    Dim line1 As AcadPolyline
    Dim line2a As AcadPolyline
    Dim line2b As AcadPolyline
    Dim line2c As AcadPolyline
    
    Set line1 = blkdef.AddPolyline(dblPnts)
    
    line1.SetBulge 2, Tan(dblAng1 * 0.25)
    line1.SetBulge 4, -Tan(dblAng2 * 0.25)
    
    varEnt = line1.Offset(cat_f)
    Set line2a = varEnt(0)

    blkdef.AddLine line1.Coordinate(0), line2a.Coordinate(0)
    blkdef.AddLine line1.Coordinate(((UBound(line1.Coordinates) + 1) / 3) - 1), line2a.Coordinate(((UBound(line2a.Coordinates) + 1) / 3) - 1)

    ReDim dblPnts(0 To 17) As Double
    
    dblPnts(0) = dblOrgX + cat_d + cat_c + cat_b - (cat_f * 0.75) + cat_TopLen: dblPnts(1) = dblOrgY + cat_e + cat_h - cat_BaseThick - (cat_f * 3#): dblPnts(2) = 0#
    dblPnts(3) = dblOrgX + cat_d + cat_c + cat_b: dblPnts(4) = dblOrgY + cat_e + cat_h - cat_BaseThick - (cat_f * 3#): dblPnts(5) = 0#
    dblPnts(6) = dblOrgX + cat_d + cat_c + cat_b - (cat_f * 0.75): dblPnts(7) = dblOrgY + cat_e + cat_h - cat_BaseThick - (cat_f * 3.75): dblPnts(8) = 0#
    dblPnts(9) = dblOrgX + cat_d + cat_c + cat_b - (cat_f * 0.75): dblPnts(10) = dblOrgY + cat_e + (cat_f * 0.75): dblPnts(11) = 0#
    dblPnts(12) = dblOrgX + cat_d + cat_c + cat_b: dblPnts(13) = dblOrgY + cat_e: dblPnts(14) = 0#
    dblPnts(15) = dblOrgX + cat_d + cat_c + cat_b - (cat_f * 0.75) + cat_a: dblPnts(16) = dblOrgY + cat_e: dblPnts(17) = 0#

    Set line1 = blkdef.AddPolyline(dblPnts)

    line1.SetBulge 1, Tan((90# * DegToRad) * 0.25)
    line1.SetBulge 3, Tan((90# * DegToRad) * 0.25)

    varEnt = line1.Offset(cat_f)
    Set line2b = varEnt(0)

    blkdef.AddLine line1.Coordinate(0), line2b.Coordinate(0)
    blkdef.AddLine line1.Coordinate(((UBound(line1.Coordinates) + 1) / 3) - 1), line2b.Coordinate(((UBound(line2b.Coordinates) + 1) / 3) - 1)

    ReDim dblPnts(0 To 11) As Double
    
    dblPnts(0) = dblOrgX + cat_d + cat_c - cat_LeftBaseLen: dblPnts(1) = dblOrgY + cat_e - cat_f: dblPnts(2) = 0#
    dblPnts(3) = dblOrgX + cat_d + cat_c + cat_b - (cat_f * 0.75) + cat_RightBaseLen: dblPnts(4) = dblOrgY + cat_e - cat_f: dblPnts(5) = 0#
    dblPnts(6) = dblOrgX + cat_d + cat_c + cat_b - (cat_f * 0.75) + cat_RightBaseLen: dblPnts(7) = dblOrgY + cat_e - cat_f - cat_BaseThick: dblPnts(8) = 0#
    dblPnts(9) = dblOrgX + cat_d + cat_c - cat_LeftBaseLen: dblPnts(10) = dblOrgY + cat_e - cat_f - cat_BaseThick: dblPnts(11) = 0#
    
    Set line1 = blkdef.AddPolyline(dblPnts)
    line1.Closed = True

    If hatch Then
        ReDim dblPnts(0 To 23) As Double
    
        For lngI = 6 To 17
            dblPnts(lngI - 6) = line2a.Coordinates(lngI)
        Next lngI
        For lngI = 3 To 14
            dblPnts(lngI + 9) = line2b.Coordinates(lngI)
        Next lngI
    
        Set line1 = blkdef.AddPolyline(dblPnts)
        line1.Closed = True
        
        line1.SetBulge 0, Tan(dblAng1 * 0.25)
        line1.SetBulge 2, -Tan(dblAng2 * 0.25)
        line1.SetBulge 4, Tan((90# * DegToRad) * 0.25)
        line1.SetBulge 6, Tan((90# * DegToRad) * 0.25)
    
        Dim objHatch As AcadHatch
        Dim outerLoop(0 To 0) As AcadEntity
        Set objHatch = blkdef.AddHatch(0, "ANSI31", True)
        AecDtlApplication.Recipe.SetHatchProperties "infill", objHatch
        AecDtlApplication.Recipe.SetEntityProperties "infill", objHatch
        Set outerLoop(0) = line1
        objHatch.AppendOuterLoop outerLoop
        objHatch.Evaluate
        
        line1.Delete
    End If

    ' start the jig
    Dim status As AecDtlPromptStatus
    status = AecDtlApplication.jig.StampBlock(blkdef)

    ' return the status
    AecDtlApplication.Recipe.ReturnStatus = status

End Sub
Public Sub AecDtlRcpSteelCNLintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim lngI As Long
    Dim dblAng1 As Double
    Dim dblAng2 As Double
    Dim dblAngl As Double
    Dim dblOrgX As Double
    Dim dblOrgY As Double
    Dim varEnt As Variant
    Dim varPnt1 As Variant
    Dim varPnt2 As Variant
    Dim varPnt3 As Variant
    Dim varPnt4 As Variant
    Dim varPnt5 As Variant
    Dim varPnt6 As Variant
    Dim dblR1 As Double
    Dim dblR2 As Double
    
    ' get the db values
    Dim cat_a As Double
    Dim cat_b As Double
    Dim cat_c As Double
    Dim cat_d As Double
    Dim cat_e As Double
    Dim cat_f As Double
    Dim cat_g As Double
    Dim cat_h As Double
    Dim cat_TopLen As Double
    Dim cat_BaseThick As Double
    Dim cat_BlockOff As Double
    Dim blnVertical As Boolean
    
    cat_h = AecDtlApplication.Database.GetFieldValueDoubleUnitDep("HEIGHT")
    cat_a = AecDtlApplication.Database.GetFieldValueDoubleUnitDep("CAT_A")
    cat_b = AecDtlApplication.Database.GetFieldValueDoubleUnitDep("CAT_B")
    cat_c = AecDtlApplication.Database.GetFieldValueDoubleUnitDep("CAT_C")
    cat_d = AecDtlApplication.Database.GetFieldValueDoubleUnitDep("CAT_D")
    cat_e = AecDtlApplication.Database.GetFieldValueDoubleUnitDep("CAT_E")
    cat_f = AecDtlApplication.Database.GetFieldValueDoubleUnitDep("CAT_F")
    cat_g = AecDtlApplication.Database.GetFieldValueDoubleUnitDep("CAT_G")
    
    If cat_b = 0# Then
        cat_c = cat_c - (cat_f * 0.75)
        cat_b = cat_f * 3.5
        cat_a = cat_a - (cat_f * 2.75)
        blnVertical = True
    Else
        blnVertical = False
    End If
    
    ' get the palette values
    Dim hatch As Boolean
    hatch = AecDtlApplication.Palette.GetPropertyValueBool("doHatch")
    
    cat_TopLen = AecDtlApplication.Recipe.GetDataValueDoubleUnitDep("boundary", "TopLength")
    cat_BaseThick = AecDtlApplication.Recipe.GetDataValueDoubleUnitDep("boundary", "BaseThick")
    cat_BlockOff = AecDtlApplication.Recipe.GetDataValueDoubleUnitDep("boundary", "BlockOff")
    
    dblOrgX = -(cat_d + cat_c): dblOrgY = -cat_e
    
    varPnt1 = Array(CDbl(dblOrgX + cat_d + cat_c), CDbl(dblOrgY + cat_e + (cat_f * 0.75)), CDbl(0#))
    varPnt2 = Array(CDbl(dblOrgX + cat_d + cat_c + cat_b), CDbl(dblOrgY + cat_e + cat_h - cat_BaseThick - (cat_f * 3.75)), CDbl(0#))
    
    dblR1 = cat_f * 0.75
    dblR2 = cat_f * 2.75
    dblAngl = CDLAngle(varPnt1, varPnt2)

    If CDLApproxEqual(dblR1 + dblR2, 0#, 0.0001) Then
        dblAng1 = (90# * DegToRad) + dblAngl
    Else
        dblAng1 = (CDLArcCos(dblR1 / (CDLDist(varPnt1, varPnt2) * (dblR1 / (dblR1 + dblR2)))) * -1#) + dblAngl
    End If

    varPnt3 = CDLPolar(varPnt1, dblAng1, dblR1)
    varPnt5 = CDLPolar(varPnt1, 270# * DegToRad, dblR1)
    varPnt4 = CDLPolar(varPnt2, dblAng1 + (180# * DegToRad), dblR2)
    varPnt6 = CDLPolar(varPnt2, 90# * DegToRad, dblR2)
    
    dblAng1 = Abs((270# * DegToRad) - CDLAngle(varPnt1, varPnt3))
    dblAng2 = CDLAngle(varPnt2, varPnt4) - (90# * DegToRad)
    
    varPnt1 = Array(CDbl(0#), CDbl(0#), CDbl(0#)): varPnt2 = varPnt1
    
    ReDim dblPnts(0 To 20) As Double
    
    dblPnts(0) = dblOrgX: dblPnts(1) = dblOrgY: dblPnts(2) = 0#
    dblPnts(3) = dblOrgX + cat_d: dblPnts(4) = dblOrgY + cat_e: dblPnts(5) = 0#
    
    dblPnts(6) = dblOrgX + cat_d + cat_c: dblPnts(7) = dblOrgY + cat_e: dblPnts(8) = 0#
    dblPnts(9) = varPnt3(0): dblPnts(10) = varPnt3(1): dblPnts(11) = 0#
    
    dblPnts(12) = varPnt4(0): dblPnts(13) = varPnt4(1): dblPnts(14) = 0#
    dblPnts(15) = dblOrgX + cat_d + cat_c + cat_b: dblPnts(16) = dblOrgY + cat_e + cat_h - cat_BaseThick - cat_f: dblPnts(17) = 0#
    
    dblPnts(18) = dblOrgX + cat_d + cat_c + cat_b + cat_a: dblPnts(19) = dblOrgY + cat_e + cat_h - cat_BaseThick - cat_f: dblPnts(20) = 0#
    
    Dim line1 As AcadPolyline
    Dim line2a As AcadPolyline
    Dim line2b As AcadPolyline
    Dim line2c As AcadPolyline
    
    Set line1 = blkdef.AddPolyline(dblPnts)
    
    If Not blnVertical Then
        line1.SetBulge 2, Tan(dblAng1 * 0.25)
    Else
        line1.SetBulge 2, Tan(22.5 * DegToRad)
    End If
    line1.SetBulge 4, -Tan(dblAng2 * 0.25)
    
    varEnt = line1.Offset(cat_f)
    Set line2a = varEnt(0)

    blkdef.AddLine line1.Coordinate(0), line2a.Coordinate(0)
    blkdef.AddLine line1.Coordinate(((UBound(line1.Coordinates) + 1) / 3) - 1), line2a.Coordinate(((UBound(line2a.Coordinates) + 1) / 3) - 1)

    ReDim dblPnts(0 To 17) As Double

    dblPnts(0) = dblOrgX + cat_d + cat_c + cat_b + cat_a: dblPnts(1) = dblOrgY + cat_e + cat_h - cat_BaseThick - (cat_f * 3#): dblPnts(2) = 0#
    dblPnts(3) = dblOrgX + cat_d + cat_c + cat_b + cat_a - cat_TopLen + (cat_f * 0.75): dblPnts(4) = dblOrgY + cat_e + cat_h - cat_BaseThick - (cat_f * 3#): dblPnts(5) = 0#
    dblPnts(6) = dblOrgX + cat_d + cat_c + cat_b + cat_a - cat_TopLen: dblPnts(7) = dblOrgY + cat_e + cat_h - cat_BaseThick - (cat_f * 3.75): dblPnts(8) = 0#
    dblPnts(9) = dblOrgX + cat_d + cat_c + cat_b + cat_a - cat_TopLen: dblPnts(10) = dblOrgY + cat_e + (cat_f * 0.75): dblPnts(11) = 0#
    dblPnts(12) = dblOrgX + cat_d + cat_c + cat_b + cat_a - cat_TopLen + (cat_f * 0.75): dblPnts(13) = dblOrgY + cat_e: dblPnts(14) = 0#
    dblPnts(15) = dblOrgX + cat_d + cat_c + cat_b + cat_a: dblPnts(16) = dblOrgY + cat_e: dblPnts(17) = 0#

    Set line1 = blkdef.AddPolyline(dblPnts)

    line1.SetBulge 1, Tan((90# * DegToRad) * 0.25)
    line1.SetBulge 3, Tan((90# * DegToRad) * 0.25)

    varEnt = line1.Offset(cat_f)
    Set line2b = varEnt(0)

    blkdef.AddLine line1.Coordinate(0), line2b.Coordinate(0)
    blkdef.AddLine line1.Coordinate(((UBound(line1.Coordinates) + 1) / 3) - 1), line2b.Coordinate(((UBound(line2b.Coordinates) + 1) / 3) - 1)

    ReDim dblPnts(0 To 11) As Double

    dblPnts(0) = dblOrgX + cat_d + cat_g: dblPnts(1) = dblOrgY + cat_e - cat_f: dblPnts(2) = 0#
    dblPnts(3) = dblOrgX + cat_d + cat_c + cat_b + cat_a: dblPnts(4) = dblOrgY + cat_e - cat_f: dblPnts(5) = 0#
    dblPnts(6) = dblOrgX + cat_d + cat_c + cat_b + cat_a: dblPnts(7) = dblOrgY + cat_e - cat_f - cat_BaseThick: dblPnts(8) = 0#
    dblPnts(9) = dblOrgX + cat_d + cat_g: dblPnts(10) = dblOrgY + cat_e - cat_f - cat_BaseThick: dblPnts(11) = 0#

    Set line1 = blkdef.AddPolyline(dblPnts)
    line1.Closed = True

    If hatch Then

        ReDim dblPnts(0 To 11) As Double
    
        varPnt1 = Array(CDbl(dblOrgX + cat_d + cat_c + (cat_f * 1.75)), CDbl(dblOrgY + cat_e - cat_f), CDbl(0#))
        varPnt2 = Array(CDbl(dblOrgX + cat_d + cat_c + cat_b + cat_a - cat_TopLen - cat_f - cat_BlockOff), CDbl(dblOrgY + cat_e - cat_f + cat_h - cat_f - cat_BaseThick), CDbl(0#))
        varPnt5 = Array(CDbl(dblOrgX + cat_d + cat_c + cat_b + cat_a - cat_f - cat_TopLen), CDbl(0#), CDbl(0#))
        varPnt6 = Array(CDbl(dblOrgX + cat_d + cat_c + cat_b + cat_a - cat_f - cat_TopLen), CDbl(10#), CDbl(0#))
        CDLIntLineLine varPnt2, CDLPolar(varPnt2, CDLAngle(varPnt1, varPnt2) - (90# * DegToRad), 10#), varPnt5, varPnt6, varPnt3
        varPnt5 = Array(CDbl(0#), CDbl(cat_e - cat_f), CDbl(0#))
        varPnt6 = Array(CDbl(10#), CDbl(cat_e - cat_f), CDbl(0#))
        CDLIntLineLine varPnt3, CDLPolar(varPnt3, CDLAngle(varPnt2, varPnt1), 10#), varPnt5, varPnt6, varPnt4
    
        dblPnts(0) = varPnt1(0): dblPnts(1) = varPnt1(1): dblPnts(2) = 0#
        dblPnts(3) = varPnt2(0): dblPnts(4) = varPnt2(1): dblPnts(5) = 0#
        dblPnts(6) = varPnt3(0): dblPnts(7) = varPnt3(1): dblPnts(8) = 0#
        dblPnts(9) = varPnt4(0): dblPnts(10) = varPnt4(1): dblPnts(11) = 0#

        Set line1 = blkdef.AddPolyline(dblPnts)
        line1.Closed = True
        AecDtlApplication.Recipe.SetEntityProperties "infill", line1

        Dim objHatch As AcadHatch
        Dim outerLoop(0 To 0) As AcadEntity
        Set objHatch = blkdef.AddHatch(0, "ANSI31", True)
        AecDtlApplication.Recipe.SetHatchProperties "infill", objHatch
        AecDtlApplication.Recipe.SetEntityProperties "infill", objHatch
        Set outerLoop(0) = line1
        objHatch.AppendOuterLoop outerLoop
        objHatch.Evaluate
    
    End If

    ' start the jig
    Dim status As AecDtlPromptStatus
    status = AecDtlApplication.jig.StampBlock(blkdef)

    ' return the status
    AecDtlApplication.Recipe.ReturnStatus = status

End Sub
Public Sub AecDtlRcpSteelCNELintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim lngI As Long
    Dim dblAng1 As Double
    Dim dblAng2 As Double
    Dim dblAngl As Double
    Dim dblOrgX As Double
    Dim dblOrgY As Double
    Dim varEnt As Variant
    Dim varPnt1 As Variant
    Dim varPnt2 As Variant
    Dim varPnt3 As Variant
    Dim varPnt4 As Variant
    Dim varPnt5 As Variant
    Dim varPnt6 As Variant
    Dim dblR1 As Double
    Dim dblR2 As Double
    
    ' get the db values
    Dim cat_a As Double
    Dim cat_b As Double
    Dim cat_f As Double
    Dim cat_h As Double
    Dim cat_TopLen As Double
    Dim cat_BaseThick As Double
    Dim cat_BlockOff As Double
    
    cat_h = AecDtlApplication.Database.GetFieldValueDoubleUnitDep("HEIGHT")
    cat_a = AecDtlApplication.Database.GetFieldValueDoubleUnitDep("CAT_A")
    cat_b = AecDtlApplication.Database.GetFieldValueDoubleUnitDep("CAT_B")
    cat_f = AecDtlApplication.Database.GetFieldValueDoubleUnitDep("CAT_F")
    
    ' get the palette values
    Dim hatch As Boolean
    hatch = AecDtlApplication.Palette.GetPropertyValueBool("doHatch")
    
    cat_TopLen = AecDtlApplication.Recipe.GetDataValueDoubleUnitDep("boundary", "TopLength")
    cat_BaseThick = AecDtlApplication.Recipe.GetDataValueDoubleUnitDep("boundary", "BaseThick")
    cat_BlockOff = AecDtlApplication.Recipe.GetDataValueDoubleUnitDep("boundary", "BlockOff")
    
    dblOrgX = -cat_b: dblOrgY = -(cat_f * 0.75)
    
    ReDim dblPnts(0 To 17) As Double
    
    dblPnts(0) = dblOrgX + cat_b - cat_TopLen: dblPnts(1) = dblOrgY: dblPnts(2) = 0#
    dblPnts(3) = dblOrgX + cat_b - (cat_f * 0.75): dblPnts(4) = dblOrgY: dblPnts(5) = 0#
    dblPnts(6) = dblOrgX + cat_b: dblPnts(7) = dblOrgY + (cat_f * 0.75): dblPnts(8) = 0#
    dblPnts(9) = dblOrgX + cat_b: dblPnts(10) = dblOrgY + cat_h - (cat_f * 2.75) - cat_BaseThick: dblPnts(11) = 0#
    dblPnts(12) = dblOrgX + cat_b + (cat_f * 1.75): dblPnts(13) = dblOrgY + cat_h - cat_BaseThick - cat_f: dblPnts(14) = 0#
    dblPnts(15) = dblOrgX + cat_b + cat_a: dblPnts(16) = dblOrgY + cat_h - cat_BaseThick - cat_f: dblPnts(17) = 0#
    
    Dim line1 As AcadPolyline
    Dim line2a As AcadPolyline
    Dim line2b As AcadPolyline
    Dim line2c As AcadPolyline
    
    Set line1 = blkdef.AddPolyline(dblPnts)
    
    line1.SetBulge 1, Tan((90# * DegToRad) * 0.25)
    line1.SetBulge 3, -Tan((90# * DegToRad) * 0.25)
    
    varEnt = line1.Offset(cat_f)
    Set line2a = varEnt(0)

    blkdef.AddLine line1.Coordinate(0), line2a.Coordinate(0)
    blkdef.AddLine line1.Coordinate(((UBound(line1.Coordinates) + 1) / 3) - 1), line2a.Coordinate(((UBound(line2a.Coordinates) + 1) / 3) - 1)

    ReDim dblPnts(0 To 17) As Double

    dblPnts(0) = dblOrgX + cat_b + cat_a: dblPnts(1) = dblOrgY + cat_h - cat_BaseThick - (cat_f * 3#): dblPnts(2) = 0#
    dblPnts(3) = dblOrgX + cat_b + cat_a - cat_TopLen + (cat_f * 0.75): dblPnts(4) = dblOrgY + cat_h - cat_BaseThick - (cat_f * 3#): dblPnts(5) = 0#
    dblPnts(6) = dblOrgX + cat_b + cat_a - cat_TopLen: dblPnts(7) = dblOrgY + cat_h - cat_BaseThick - (cat_f * 3.75): dblPnts(8) = 0#
    dblPnts(9) = dblOrgX + cat_b + cat_a - cat_TopLen: dblPnts(10) = dblOrgY + (cat_f * 0.75): dblPnts(11) = 0#
    dblPnts(12) = dblOrgX + cat_b + cat_a - cat_TopLen + (cat_f * 0.75): dblPnts(13) = dblOrgY: dblPnts(14) = 0#
    dblPnts(15) = dblOrgX + cat_b + cat_a: dblPnts(16) = dblOrgY: dblPnts(17) = 0#

    Set line1 = blkdef.AddPolyline(dblPnts)

    line1.SetBulge 1, Tan((90# * DegToRad) * 0.25)
    line1.SetBulge 3, Tan((90# * DegToRad) * 0.25)

    varEnt = line1.Offset(cat_f)
    Set line2b = varEnt(0)

    blkdef.AddLine line1.Coordinate(0), line2b.Coordinate(0)
    blkdef.AddLine line1.Coordinate(((UBound(line1.Coordinates) + 1) / 3) - 1), line2b.Coordinate(((UBound(line2b.Coordinates) + 1) / 3) - 1)

    ReDim dblPnts(0 To 11) As Double

    dblPnts(0) = dblOrgX: dblPnts(1) = dblOrgY - cat_f: dblPnts(2) = 0#
    dblPnts(3) = dblOrgX + cat_b + cat_a: dblPnts(4) = dblOrgY - cat_f: dblPnts(5) = 0#
    dblPnts(6) = dblOrgX + cat_b + cat_a: dblPnts(7) = dblOrgY - cat_f - cat_BaseThick: dblPnts(8) = 0#
    dblPnts(9) = dblOrgX: dblPnts(10) = dblOrgY - cat_f - cat_BaseThick: dblPnts(11) = 0#

    Set line1 = blkdef.AddPolyline(dblPnts)
    line1.Closed = True

    If hatch Then

        ReDim dblPnts(0 To 11) As Double

        varPnt1 = Array(CDbl(dblOrgX + cat_b + cat_f), CDbl(dblOrgY - cat_f), CDbl(0#))
        varPnt2 = Array(CDbl(dblOrgX + cat_b + cat_a - cat_TopLen - cat_f - cat_BlockOff), CDbl(dblOrgY - cat_f + cat_h - cat_f - cat_BaseThick), CDbl(0#))
        varPnt5 = Array(CDbl(dblOrgX + cat_b + cat_a - cat_f - cat_TopLen), CDbl(0#), CDbl(0#))
        varPnt6 = Array(CDbl(dblOrgX + cat_b + cat_a - cat_f - cat_TopLen), CDbl(10#), CDbl(0#))
        CDLIntLineLine varPnt2, CDLPolar(varPnt2, CDLAngle(varPnt1, varPnt2) - (90# * DegToRad), 10#), varPnt5, varPnt6, varPnt3
        varPnt5 = Array(CDbl(0#), CDbl(-cat_f), CDbl(0#))
        varPnt6 = Array(CDbl(10#), CDbl(-cat_f), CDbl(0#))
        CDLIntLineLine varPnt3, CDLPolar(varPnt3, CDLAngle(varPnt2, varPnt1), 10#), varPnt5, varPnt6, varPnt4

        dblPnts(0) = varPnt1(0): dblPnts(1) = varPnt1(1): dblPnts(2) = 0#
        dblPnts(3) = varPnt2(0): dblPnts(4) = varPnt2(1): dblPnts(5) = 0#
        dblPnts(6) = varPnt3(0): dblPnts(7) = varPnt3(1): dblPnts(8) = 0#
        dblPnts(9) = varPnt4(0): dblPnts(10) = varPnt4(1): dblPnts(11) = 0#

        Set line1 = blkdef.AddPolyline(dblPnts)
        line1.Closed = True
        AecDtlApplication.Recipe.SetEntityProperties "infill", line1

        Dim objHatch As AcadHatch
        Dim outerLoop(0 To 0) As AcadEntity
        Set objHatch = blkdef.AddHatch(0, "ANSI31", True)
        AecDtlApplication.Recipe.SetHatchProperties "infill", objHatch
        AecDtlApplication.Recipe.SetEntityProperties "infill", objHatch
        Set outerLoop(0) = line1
        objHatch.AppendOuterLoop outerLoop
        objHatch.Evaluate

    End If

    ' start the jig
    Dim status As AecDtlPromptStatus
    status = AecDtlApplication.jig.StampBlock(blkdef)

    ' return the status
    AecDtlApplication.Recipe.ReturnStatus = status

End Sub
Public Sub AecDtlRcpSteelCXLLintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim lngI As Long
    Dim dblAng1 As Double
    Dim dblAng2 As Double
    Dim dblAngl As Double
    Dim dblOrgX As Double
    Dim dblOrgY As Double
    Dim varEnt As Variant
    Dim varPnt1 As Variant
    Dim varPnt2 As Variant
    Dim varPnt3 As Variant
    Dim varPnt4 As Variant
    Dim varPnt5 As Variant
    Dim varPnt6 As Variant
    Dim dblR1 As Double
    Dim dblR2 As Double
    
    ' get the db values
    Dim cat_a As Double
    Dim cat_b As Double
    Dim cat_c As Double
    Dim cat_d As Double
    Dim cat_h As Double
    Dim cat_BaseThick As Double
    
    cat_h = AecDtlApplication.Database.GetFieldValueDoubleUnitDep("HEIGHT")
    cat_a = AecDtlApplication.Database.GetFieldValueDoubleUnitDep("CAT_A")
    cat_b = AecDtlApplication.Database.GetFieldValueDoubleUnitDep("CAT_B")
    cat_c = AecDtlApplication.Database.GetFieldValueDoubleUnitDep("CAT_C")
    cat_d = AecDtlApplication.Database.GetFieldValueDoubleUnitDep("CAT_D")
    
    cat_BaseThick = AecDtlApplication.Recipe.GetDataValueDoubleUnitDep("boundary", "BaseThick")
    
    dblOrgX = -cat_a: dblOrgY = 0#
    
    ReDim dblPnts(0 To 35) As Double
    
    dblPnts(0) = dblOrgX: dblPnts(1) = dblOrgY: dblPnts(2) = 0#
    dblPnts(3) = dblOrgX + cat_a: dblPnts(4) = dblOrgY: dblPnts(5) = 0#
    dblPnts(6) = dblOrgX + cat_a: dblPnts(7) = dblOrgY + cat_d: dblPnts(8) = 0#
    dblPnts(9) = dblOrgX + cat_BaseThick + ((cat_a - cat_BaseThick) / 2#): dblPnts(10) = dblOrgY + cat_d: dblPnts(11) = 0#
    dblPnts(12) = dblOrgX + cat_BaseThick + ((cat_a - cat_BaseThick) / 2#): dblPnts(13) = dblOrgY + cat_h - (cat_d * 2#) - cat_BaseThick: dblPnts(14) = 0#
    dblPnts(15) = dblOrgX + cat_a: dblPnts(16) = dblOrgY + cat_h - (cat_d * 2#) - cat_BaseThick: dblPnts(17) = 0#
    dblPnts(18) = dblOrgX + cat_a: dblPnts(19) = dblOrgY + cat_h - cat_d - cat_BaseThick: dblPnts(20) = 0#
    dblPnts(21) = dblOrgX: dblPnts(22) = dblOrgY + cat_h - cat_d - cat_BaseThick: dblPnts(23) = 0#
    dblPnts(24) = dblOrgX: dblPnts(25) = dblOrgY + cat_h - (cat_d * 2#) - cat_BaseThick: dblPnts(26) = 0#
    dblPnts(27) = dblOrgX + ((cat_a - cat_BaseThick) / 2#): dblPnts(28) = dblOrgY + cat_h - (cat_d * 2#) - cat_BaseThick: dblPnts(29) = 0#
    dblPnts(30) = dblOrgX + ((cat_a - cat_BaseThick) / 2#): dblPnts(31) = dblOrgY + cat_d: dblPnts(32) = 0#
    dblPnts(33) = dblOrgX: dblPnts(34) = dblOrgY + cat_d: dblPnts(35) = 0#
    
    Dim line1 As AcadPolyline
    
    Set line1 = blkdef.AddPolyline(dblPnts)
    line1.Closed = True

    ReDim dblPnts(0 To 11) As Double
    
    dblPnts(0) = dblOrgX + cat_c: dblPnts(1) = dblOrgY: dblPnts(2) = 0#
    dblPnts(3) = dblOrgX + cat_c + cat_b: dblPnts(4) = dblOrgY: dblPnts(5) = 0#
    dblPnts(6) = dblOrgX + cat_c + cat_b: dblPnts(7) = dblOrgY - cat_BaseThick: dblPnts(8) = 0#
    dblPnts(9) = dblOrgX + cat_c: dblPnts(10) = dblOrgY - cat_BaseThick: dblPnts(11) = 0#
    
    Set line1 = blkdef.AddPolyline(dblPnts)
    line1.Closed = True

    ' start the jig
    Dim status As AecDtlPromptStatus
    status = AecDtlApplication.jig.StampBlock(blkdef)

    ' return the status
    AecDtlApplication.Recipe.ReturnStatus = status

End Sub
Public Sub AecDtlRcpSteelCN50LintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblOrgX As Double
    Dim dblOrgY As Double
    Dim varEnt As Variant
    
    ' get the db values
    Dim cat_a As Double
    Dim cat_f As Double
    Dim cat_h As Double
    
    cat_h = AecDtlApplication.Database.GetFieldValueDoubleUnitDep("HEIGHT")
    cat_a = AecDtlApplication.Database.GetFieldValueDoubleUnitDep("CAT_A")
    cat_f = AecDtlApplication.Database.GetFieldValueDoubleUnitDep("CAT_F")
    
    dblOrgX = -(cat_a / 2#) + cat_f: dblOrgY = -(cat_f * 0.75)
    
    ReDim dblPnts(0 To 11) As Double
    
    dblPnts(0) = dblOrgX: dblPnts(1) = dblOrgY: dblPnts(2) = 0#
    dblPnts(3) = dblOrgX + (cat_a / 2#) - (cat_f * 1.75): dblPnts(4) = dblOrgY: dblPnts(5) = 0#
    dblPnts(6) = dblOrgX + (cat_a / 2#) - cat_f: dblPnts(7) = dblOrgY + (cat_f * 0.75): dblPnts(8) = 0#
    dblPnts(9) = dblOrgX + (cat_a / 2#) - cat_f: dblPnts(10) = dblOrgY + cat_h - cat_f: dblPnts(11) = 0#
    
    Dim line1 As AcadPolyline
    Dim line2 As AcadPolyline
    
    Set line1 = blkdef.AddPolyline(dblPnts)
    
    line1.SetBulge 1, Tan(22.5 * DegToRad)
    
    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    dblPnts(0) = dblOrgX + (cat_a / 2#) + cat_f: dblPnts(1) = dblOrgY + cat_h - cat_f: dblPnts(2) = 0#
    dblPnts(3) = dblOrgX + (cat_a / 2#) + cat_f: dblPnts(4) = dblOrgY + (cat_f * 0.75): dblPnts(5) = 0#
    dblPnts(6) = dblOrgX + (cat_a / 2#) + (cat_f * 1.75): dblPnts(7) = dblOrgY: dblPnts(8) = 0#
    dblPnts(9) = dblOrgX + cat_a: dblPnts(10) = dblOrgY: dblPnts(11) = 0#
    
    Set line1 = blkdef.AddPolyline(dblPnts)
    
    line1.SetBulge 1, Tan(22.5 * DegToRad)
    
    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)
    
    ' start the jig
    Dim status As AecDtlPromptStatus
    status = AecDtlApplication.jig.StampBlock(blkdef)

    ' return the status
    AecDtlApplication.Recipe.ReturnStatus = status

End Sub
Public Sub AecDtlRcpSteelCN48LintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblOrgX As Double
    Dim dblOrgY As Double
    Dim varEnt As Variant
    
    ' get the db values
    Dim cat_b As Double
    Dim cat_c As Double
    Dim cat_f As Double
    Dim cat_h As Double
    
    cat_h = AecDtlApplication.Database.GetFieldValueDoubleUnitDep("HEIGHT")
    cat_b = AecDtlApplication.Database.GetFieldValueDoubleUnitDep("CAT_B")
    cat_c = AecDtlApplication.Database.GetFieldValueDoubleUnitDep("CAT_C")
    cat_f = AecDtlApplication.Database.GetFieldValueDoubleUnitDep("CAT_F")
    
    dblOrgX = -(cat_c + cat_b - cat_f): dblOrgY = -(cat_f * 0.75)
    
    ReDim dblPnts(0 To 17) As Double
    
    dblPnts(0) = dblOrgX: dblPnts(1) = dblOrgY: dblPnts(2) = 0#
    dblPnts(3) = dblOrgX + cat_c + cat_b - (cat_f * 1.75): dblPnts(4) = dblOrgY: dblPnts(5) = 0#
    dblPnts(6) = dblOrgX + cat_c + cat_b - cat_f: dblPnts(7) = dblOrgY + (cat_f * 0.75): dblPnts(8) = 0#
    dblPnts(9) = dblOrgX + cat_c + cat_b - cat_f: dblPnts(10) = dblOrgY + cat_h - (cat_f * 2.75): dblPnts(11) = 0#
    dblPnts(12) = dblOrgX + cat_c + cat_b - (cat_f * 1.75): dblPnts(13) = dblOrgY + cat_h - (cat_f * 2#): dblPnts(14) = 0#
    dblPnts(15) = dblOrgX + cat_c: dblPnts(16) = dblOrgY + cat_h - (cat_f * 2#): dblPnts(17) = 0#
    
    Dim line1 As AcadPolyline
    Dim line2 As AcadPolyline
    
    Set line1 = blkdef.AddPolyline(dblPnts)
    
    line1.SetBulge 1, Tan(22.5 * DegToRad)
    line1.SetBulge 3, Tan(22.5 * DegToRad)
    
    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    ' start the jig
    Dim status As AecDtlPromptStatus
    status = AecDtlApplication.jig.StampBlock(blkdef)

    ' return the status
    AecDtlApplication.Recipe.ReturnStatus = status

End Sub
Public Sub AecDtlRcpSteelCN100LintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblOrgX As Double
    Dim dblOrgY As Double
    Dim varEnt As Variant
    
    ' get the db values
    Dim cat_a As Double
    Dim cat_f As Double
    Dim cat_h As Double
    
    cat_h = AecDtlApplication.Database.GetFieldValueDoubleUnitDep("HEIGHT")
    cat_a = AecDtlApplication.Database.GetFieldValueDoubleUnitDep("CAT_A")
    cat_f = AecDtlApplication.Database.GetFieldValueDoubleUnitDep("CAT_F")
    
    dblOrgX = 0#: dblOrgY = 0#
    
    ReDim dblPnts(0 To 17) As Double
    
    dblPnts(0) = dblOrgX + cat_f: dblPnts(1) = dblOrgY + cat_h: dblPnts(2) = 0#
    dblPnts(3) = dblOrgX + cat_f: dblPnts(4) = dblOrgY + (cat_f * 1.75): dblPnts(5) = 0#
    dblPnts(6) = dblOrgX + (cat_f * 1.75): dblPnts(7) = dblOrgY + cat_f: dblPnts(8) = 0#
    dblPnts(9) = dblOrgX + cat_a - (cat_f * 1.75): dblPnts(10) = dblOrgY + cat_f: dblPnts(11) = 0#
    dblPnts(12) = dblOrgX + cat_a - cat_f: dblPnts(13) = dblOrgY + (cat_f * 1.75): dblPnts(14) = 0#
    dblPnts(15) = dblOrgX + cat_a - cat_f: dblPnts(16) = dblOrgY + cat_h: dblPnts(17) = 0#
    
    Dim line1 As AcadPolyline
    Dim line2 As AcadPolyline
    
    Set line1 = blkdef.AddPolyline(dblPnts)
    
    line1.SetBulge 1, Tan(22.5 * DegToRad)
    line1.SetBulge 3, Tan(22.5 * DegToRad)
    
    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    ' start the jig
    Dim status As AecDtlPromptStatus
    status = AecDtlApplication.jig.StampBlock(blkdef)

    ' return the status
    AecDtlApplication.Recipe.ReturnStatus = status

End Sub
Public Sub AecDtlRcpSteelCN5XLintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblOrgX As Double
    Dim dblOrgY As Double
    Dim varEnt As Variant
    Dim cat_TopLen As Double
    
    ' get the db values
    Dim cat_a As Double
    Dim cat_f As Double
    Dim cat_h As Double
    
    cat_h = AecDtlApplication.Database.GetFieldValueDoubleUnitDep("HEIGHT")
    cat_a = AecDtlApplication.Database.GetFieldValueDoubleUnitDep("CAT_A")
    cat_f = AecDtlApplication.Database.GetFieldValueDoubleUnitDep("CAT_F")
    
    cat_TopLen = AecDtlApplication.Recipe.GetDataValueDoubleUnitDep("boundary", "TopLen")
    
    dblOrgX = 0#: dblOrgY = 0#
    
    ReDim dblPnts(0 To 17) As Double
    
    dblPnts(0) = dblOrgX + cat_a: dblPnts(1) = dblOrgY + cat_h - cat_f: dblPnts(2) = 0#
    dblPnts(3) = dblOrgX + (cat_f * 1.75): dblPnts(4) = dblOrgY + cat_h - cat_f: dblPnts(5) = 0#
    dblPnts(6) = dblOrgX + cat_f: dblPnts(7) = dblOrgY + cat_h - (cat_f * 1.75): dblPnts(8) = 0#
    dblPnts(9) = dblOrgX + cat_f: dblPnts(10) = dblOrgY + (cat_f * 1.75): dblPnts(11) = 0#
    dblPnts(12) = dblOrgX + (cat_f * 1.75): dblPnts(13) = dblOrgY + cat_f: dblPnts(14) = 0#
    dblPnts(15) = dblOrgX + cat_a: dblPnts(16) = dblOrgY + cat_f: dblPnts(17) = 0#
    
    Dim line1 As AcadPolyline
    Dim line2 As AcadPolyline
    
    Set line1 = blkdef.AddPolyline(dblPnts)
    
    line1.SetBulge 1, Tan(22.5 * DegToRad)
    line1.SetBulge 3, Tan(22.5 * DegToRad)
    
    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    dblPnts(0) = dblOrgX + cat_a: dblPnts(1) = dblOrgY + cat_h - (cat_f * 2#): dblPnts(2) = 0#
    dblPnts(3) = dblOrgX + cat_a - cat_TopLen + (cat_f * 0.75): dblPnts(4) = dblOrgY + cat_h - (cat_f * 2#): dblPnts(5) = 0#
    dblPnts(6) = dblOrgX + cat_a - cat_TopLen: dblPnts(7) = dblOrgY + cat_h - (cat_f * 2.75): dblPnts(8) = 0#
    dblPnts(9) = dblOrgX + cat_a - cat_TopLen: dblPnts(10) = dblOrgY + (cat_f * 2.75): dblPnts(11) = 0#
    dblPnts(12) = dblOrgX + cat_a - cat_TopLen + (cat_f * 0.75): dblPnts(13) = dblOrgY + (cat_f * 2#): dblPnts(14) = 0#
    dblPnts(15) = dblOrgX + cat_a: dblPnts(16) = dblOrgY + (cat_f * 2#): dblPnts(17) = 0#
    
    Set line1 = blkdef.AddPolyline(dblPnts)
    
    line1.SetBulge 1, Tan(22.5 * DegToRad)
    line1.SetBulge 3, Tan(22.5 * DegToRad)
    
    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    ' start the jig
    Dim status As AecDtlPromptStatus
    status = AecDtlApplication.jig.StampBlock(blkdef)

    ' return the status
    AecDtlApplication.Recipe.ReturnStatus = status

End Sub
Public Sub AecDtlRcpSteelCNZLintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblOrgX As Double
    Dim dblOrgY As Double
    Dim varEnt As Variant
    
    ' get the db values
    Dim cat_b As Double
    Dim cat_c As Double
    Dim cat_d As Double
    Dim cat_e As Double
    Dim cat_f As Double
    Dim cat_h As Double
    
    cat_h = AecDtlApplication.Database.GetFieldValueDoubleUnitDep("HEIGHT")
    cat_b = AecDtlApplication.Database.GetFieldValueDoubleUnitDep("CAT_B")
    cat_c = AecDtlApplication.Database.GetFieldValueDoubleUnitDep("CAT_C")
    cat_d = AecDtlApplication.Database.GetFieldValueDoubleUnitDep("CAT_D")
    cat_e = AecDtlApplication.Database.GetFieldValueDoubleUnitDep("CAT_E")
    cat_f = AecDtlApplication.Database.GetFieldValueDoubleUnitDep("CAT_F")
    
    dblOrgX = -(cat_d + cat_c): dblOrgY = -(cat_e + (cat_f * 0.75))
    
    Dim dblPnts(0 To 17) As Double
    
    dblPnts(0) = dblOrgX: dblPnts(1) = dblOrgY: dblPnts(2) = 0#
    dblPnts(3) = dblOrgX + cat_d: dblPnts(4) = dblOrgY + cat_e: dblPnts(5) = 0#
    dblPnts(6) = dblOrgX + cat_d + cat_c - (cat_f * 0.75): dblPnts(7) = dblOrgY + cat_e: dblPnts(8) = 0#
    dblPnts(9) = dblOrgX + cat_d + cat_c: dblPnts(10) = dblOrgY + cat_e + (cat_f * 0.75): dblPnts(11) = 0#
    dblPnts(12) = dblOrgX + cat_d + cat_c: dblPnts(13) = dblOrgY + cat_e + cat_h - cat_f - cat_d: dblPnts(14) = 0#
    dblPnts(15) = dblOrgX + cat_d + cat_c + cat_b: dblPnts(16) = dblOrgY + cat_e + cat_h - cat_f: dblPnts(17) = 0#
    
    Dim line1 As AcadPolyline
    Dim line2 As AcadPolyline

    Set line1 = blkdef.AddPolyline(dblPnts)

    line1.SetBulge 2, 0.414213562373095

    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    ' start the jig
    Dim status As AecDtlPromptStatus
    status = AecDtlApplication.jig.StampBlock(blkdef)

    ' return the status
    AecDtlApplication.Recipe.ReturnStatus = status

End Sub
Public Sub AecDtlRcpSteelCN23LintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblAng1 As Double
    Dim dblAng2 As Double
    Dim dblAngl As Double
    Dim dblOrgX As Double
    Dim dblOrgY As Double
    Dim varEnt As Variant
    Dim varPnt1 As Variant
    Dim varPnt2 As Variant
    Dim varPnt3 As Variant
    Dim varPnt4 As Variant
    Dim varPnt5 As Variant
    Dim varPnt6 As Variant
    Dim dblR1 As Double
    Dim dblR2 As Double
    
    ' get the db values
    Dim cat_a As Double
    Dim cat_b As Double
    Dim cat_c As Double
    Dim cat_d As Double
    Dim cat_e As Double
    Dim cat_f As Double
    Dim cat_g As Double
    Dim cat_h As Double
    Dim cat_TopLip As Double
    Dim cat_BaseThick As Double
    
    cat_h = AecDtlApplication.Database.GetFieldValueDoubleUnitDep("HEIGHT")
    cat_a = AecDtlApplication.Database.GetFieldValueDoubleUnitDep("CAT_A")
    cat_b = AecDtlApplication.Database.GetFieldValueDoubleUnitDep("CAT_B")
    cat_c = AecDtlApplication.Database.GetFieldValueDoubleUnitDep("CAT_C")
    cat_d = AecDtlApplication.Database.GetFieldValueDoubleUnitDep("CAT_D")
    cat_e = AecDtlApplication.Database.GetFieldValueDoubleUnitDep("CAT_E")
    cat_f = AecDtlApplication.Database.GetFieldValueDoubleUnitDep("CAT_F")
    cat_g = AecDtlApplication.Database.GetFieldValueDoubleUnitDep("CAT_G")
    
    cat_TopLip = AecDtlApplication.Recipe.GetDataValueDoubleUnitDep("boundary", "TopLip")
    cat_BaseThick = AecDtlApplication.Recipe.GetDataValueDoubleUnitDep("boundary", "BaseThick")
    
    dblOrgX = -(cat_d + cat_c): dblOrgY = -cat_e
    
    varPnt1 = Array(CDbl(dblOrgX + cat_d + cat_c), CDbl(dblOrgY + cat_e + (cat_f * 0.75)), CDbl(0#))
    varPnt2 = Array(CDbl(dblOrgX + cat_d + cat_c + cat_b - cat_BaseThick - (cat_f * 1.75)), CDbl(dblOrgY + cat_e + cat_h - cat_BaseThick - cat_f - cat_a - cat_TopLip), CDbl(0#))
    
    dblR1 = cat_f * 0.75
    dblR2 = cat_f * 0.75
    dblAngl = CDLAngle(varPnt1, varPnt2)

    dblAng1 = (-90# * DegToRad) + dblAngl

    varPnt3 = CDLPolar(varPnt1, dblAng1, dblR1)
    varPnt5 = CDLPolar(varPnt1, 270# * DegToRad, dblR1)
    varPnt4 = CDLPolar(varPnt2, dblAng1, dblR2)
    varPnt6 = CDLPolar(varPnt2, 90# * DegToRad, dblR2)
    
    dblAng1 = Abs((270# * DegToRad) - CDLAngle(varPnt1, varPnt3))
    dblAng2 = (360# * DegToRad) - CDLAngle(varPnt2, varPnt4)
    
    ReDim dblPnts(0 To 20) As Double
    
    dblPnts(0) = dblOrgX: dblPnts(1) = dblOrgY: dblPnts(2) = 0#
    dblPnts(3) = dblOrgX + cat_d: dblPnts(4) = dblOrgY + cat_e: dblPnts(5) = 0#
    
    dblPnts(6) = dblOrgX + cat_d + cat_c: dblPnts(7) = dblOrgY + cat_e: dblPnts(8) = 0#
    dblPnts(9) = varPnt3(0): dblPnts(10) = varPnt3(1): dblPnts(11) = 0#
    
    dblPnts(12) = varPnt4(0): dblPnts(13) = varPnt4(1): dblPnts(14) = 0#
    dblPnts(15) = dblOrgX + cat_d + cat_c + cat_b - cat_BaseThick - cat_f: dblPnts(16) = dblOrgY + cat_e + cat_h - cat_BaseThick - cat_f - cat_TopLip - cat_a: dblPnts(17) = 0#
    
    dblPnts(18) = dblOrgX + cat_d + cat_c + cat_b - cat_BaseThick - cat_f: dblPnts(19) = dblOrgY + cat_e + cat_h - cat_BaseThick - cat_f - cat_TopLip: dblPnts(20) = 0#
    
    Dim line1 As AcadPolyline
    Dim line2 As AcadPolyline
    
    Set line1 = blkdef.AddPolyline(dblPnts)
    
    line1.SetBulge 2, Tan(dblAng1 * 0.25)
    line1.SetBulge 4, Tan(dblAng2 * 0.25)
    
    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    ReDim dblPnts(0 To 11) As Double

    dblPnts(0) = dblOrgX + cat_d + cat_g: dblPnts(1) = dblOrgY + cat_e - cat_f: dblPnts(2) = 0#
    dblPnts(3) = dblOrgX + cat_d + cat_c + cat_b - (cat_BaseThick * 1.75): dblPnts(4) = dblOrgY + cat_e - cat_f: dblPnts(5) = 0#
    dblPnts(6) = dblOrgX + cat_d + cat_c + cat_b - cat_BaseThick: dblPnts(7) = dblOrgY + cat_e - cat_f + (cat_BaseThick * 0.75): dblPnts(8) = 0#
    dblPnts(9) = dblOrgX + cat_d + cat_c + cat_b - cat_BaseThick: dblPnts(10) = dblOrgY + cat_e - cat_f + cat_h: dblPnts(11) = 0#

    Set line1 = blkdef.AddPolyline(dblPnts)

    line1.SetBulge 1, Tan((90# * DegToRad) * 0.25)

    varEnt = line1.Offset(cat_BaseThick)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    ' start the jig
    Dim status As AecDtlPromptStatus
    status = AecDtlApplication.jig.StampBlock(blkdef)

    ' return the status
    AecDtlApplication.Recipe.ReturnStatus = status

End Sub
Public Sub AecDtlRcpSteelCTFLintelSection()

    Dim dblPnt(0 To 2) As Double
    Dim blkdef As AcadBlock
    dblPnt(0) = 0#
    dblPnt(1) = 0#
    dblPnt(2) = 0#
    Set blkdef = ThisDrawing.Blocks.Add(dblPnt, "*U")
    
    Dim dblOrgX As Double
    Dim dblOrgY As Double
    Dim varEnt As Variant
    
    ' get the db values
    Dim cat_a As Double
    Dim cat_b As Double
    Dim cat_c As Double
    Dim cat_d As Double
    Dim cat_e As Double
    Dim cat_f As Double
    Dim cat_h As Double
    Dim cat_TopLen As Double
    
    cat_h = AecDtlApplication.Database.GetFieldValueDoubleUnitDep("HEIGHT")
    cat_a = AecDtlApplication.Database.GetFieldValueDoubleUnitDep("CAT_A")
    cat_b = AecDtlApplication.Database.GetFieldValueDoubleUnitDep("CAT_B")
    cat_c = AecDtlApplication.Database.GetFieldValueDoubleUnitDep("CAT_C")
    cat_d = AecDtlApplication.Database.GetFieldValueDoubleUnitDep("CAT_D")
    cat_e = AecDtlApplication.Database.GetFieldValueDoubleUnitDep("CAT_E")
    cat_f = AecDtlApplication.Database.GetFieldValueDoubleUnitDep("CAT_F")
    
    cat_TopLen = AecDtlApplication.Recipe.GetDataValueDoubleUnitDep("boundary", "TopLen")
    
    dblOrgX = -(cat_d + cat_c): dblOrgY = -(cat_e + (cat_f * 0.75))
    
    Dim dblPnts(0 To 20) As Double
    
    dblPnts(0) = dblOrgX: dblPnts(1) = dblOrgY: dblPnts(2) = 0#
    dblPnts(3) = dblOrgX + cat_d: dblPnts(4) = dblOrgY + cat_e: dblPnts(5) = 0#
    dblPnts(6) = dblOrgX + cat_d + cat_c - (cat_f * 0.75): dblPnts(7) = dblOrgY + cat_e: dblPnts(8) = 0#
    dblPnts(9) = dblOrgX + cat_d + cat_c: dblPnts(10) = dblOrgY + cat_e + (cat_f * 0.75): dblPnts(11) = 0#
    dblPnts(12) = dblOrgX + cat_d + cat_c: dblPnts(13) = dblOrgY + cat_e + cat_a: dblPnts(14) = 0#
    dblPnts(15) = dblOrgX + cat_d + cat_c + cat_b - cat_f: dblPnts(16) = dblOrgY + cat_e + cat_h - cat_f - cat_TopLen: dblPnts(17) = 0#
    dblPnts(18) = dblOrgX + cat_d + cat_c + cat_b - cat_f: dblPnts(19) = dblOrgY + cat_e + cat_h - cat_f: dblPnts(20) = 0#
    
    Dim line1 As AcadPolyline
    Dim line2 As AcadPolyline

    Set line1 = blkdef.AddPolyline(dblPnts)

    line1.SetBulge 2, 0.414213562373095

    varEnt = line1.Offset(cat_f)
    Set line2 = varEnt(0)

    blkdef.AddLine line1.Coordinate(0), line2.Coordinate(0)
    blkdef.AddLine line1.Coordinate(((UBound(line1.Coordinates) + 1) / 3) - 1), line2.Coordinate(((UBound(line2.Coordinates) + 1) / 3) - 1)

    ' start the jig
    Dim status As AecDtlPromptStatus
    status = AecDtlApplication.jig.StampBlock(blkdef)

    ' return the status
    AecDtlApplication.Recipe.ReturnStatus = status

End Sub
Public Sub AecDtlRcpWHMJoistHangerSection()

    Dim dblPnt(0 To 2) As Double
    Dim blkdef As AcadBlock
    dblPnt(0) = 0#
    dblPnt(1) = 0#
    dblPnt(2) = 0#
    Set blkdef = ThisDrawing.Blocks.Add(dblPnt, "*U")
    
    Dim varEnt As Variant
    
    ' get the db values
    Dim dHeight As Double
    Dim dBase As Double
    Dim dFlange As Double
    Dim dGauge As Double
    Dim iNumNails As Integer
    Dim dNailDia As Double
    Dim dNailSpace As Double
    
    Dim varPnt1 As Variant
    Dim varPnt2 As Variant
    
    Dim lngI As Long
    
    dHeight = AecDtlApplication.Database.GetFieldValueDoubleUnitDep("HEIGHT")
    dBase = AecDtlApplication.Database.GetFieldValueDoubleUnitDep("BASE")
    dFlange = AecDtlApplication.Database.GetFieldValueDoubleUnitDep("FLANGE")
    dGauge = AecDtlApplication.Database.GetFieldValueDoubleUnitDep("DGAUGE")
    iNumNails = AecDtlApplication.Database.GetFieldValueLong("NUM_NAILS")
    dNailDia = AecDtlApplication.Database.GetFieldValueDoubleUnitDep("NAIL_DIA")
    
    dNailSpace = AecDtlApplication.Recipe.GetDataValueDoubleUnitDep("boundary", "NailSpace")
    
    dblPnt(0) = 0#
    dblPnt(1) = 0#
    dblPnt(2) = 0#
    varPnt1 = dblPnt
    varPnt2 = dblPnt
    
    varPnt1(0) = -dFlange
    blkdef.AddLine varPnt1, varPnt2
    
    varPnt2 = varPnt1
    varPnt2(1) = varPnt2(1) + dGauge
    blkdef.AddLine varPnt1, varPnt2
    
    varPnt1 = varPnt2
    varPnt2(0) = varPnt2(0) + dFlange + dGauge
    blkdef.AddLine varPnt1, varPnt2
    
    varPnt1 = varPnt2
    varPnt2(1) = varPnt2(1) - dFlange * (2# / 3#)
    blkdef.AddLine varPnt1, varPnt2
    
    varPnt1 = varPnt2
    varPnt2(0) = varPnt2(0) - dGauge
    blkdef.AddLine varPnt1, varPnt2
    
    varPnt1 = varPnt2
    varPnt2(1) = 0#
    blkdef.AddLine varPnt1, varPnt2
    
    varPnt1 = dblPnt
    varPnt1(0) = dGauge
    varPnt2 = dblPnt
    varPnt2(0) = dGauge + dBase
    blkdef.AddLine varPnt1, varPnt2
    
    varPnt1 = varPnt2
    varPnt2(1) = varPnt2(1) - dHeight - dGauge
    blkdef.AddLine varPnt1, varPnt2
    
    varPnt1 = varPnt2
    varPnt2(0) = varPnt2(0) - dBase
    blkdef.AddLine varPnt1, varPnt2
    
    varPnt1 = varPnt2
    varPnt2(1) = 0#
    blkdef.AddLine varPnt1, varPnt2
    
    varPnt1(0) = dGauge
    varPnt1(1) = -dHeight#
    varPnt2(0) = dBase + dGauge
    varPnt2(1) = -dHeight#
    AecDtlApplication.Recipe.SetEntityProperties "hide", blkdef.AddLine(varPnt1, varPnt2)
    
    varPnt1(0) = dGauge + (dBase * 0.75)
    varPnt1(1) = -(dHeight * 0.7)
    For lngI = 1 To iNumNails
        blkdef.AddCircle varPnt1, dNailDia
        varPnt1(1) = varPnt1(1) + dNailSpace
    Next lngI
    
    ' start the jig
    Dim status As AecDtlPromptStatus
    status = AecDtlApplication.jig.StampBlock(blkdef)

    ' return the status
    AecDtlApplication.Recipe.ReturnStatus = status

End Sub
Public Sub AecDtlRcpHJHMJoistHangerSection()

    Dim dblPnt(0 To 2) As Double
    Dim blkdef As AcadBlock
    dblPnt(0) = 0#
    dblPnt(1) = 0#
    dblPnt(2) = 0#
    Set blkdef = ThisDrawing.Blocks.Add(dblPnt, "*U")
    
    Dim varEnt As Variant
    
    ' get the db values
    Dim dHeight As Double
    Dim dBase As Double
    Dim dFlange As Double
    Dim dGauge As Double
    Dim iNumNails As Integer
    Dim dNailDia As Double
    
    Dim varPnt1 As Variant
    Dim varPnt2 As Variant
    
    Dim lngI As Long
    
    dHeight = AecDtlApplication.Database.GetFieldValueDoubleUnitDep("HEIGHT")
    dBase = AecDtlApplication.Database.GetFieldValueDoubleUnitDep("BASE")
    dFlange = AecDtlApplication.Database.GetFieldValueDoubleUnitDep("FLANGE")
    dGauge = AecDtlApplication.Database.GetFieldValueDoubleUnitDep("DGAUGE")
    iNumNails = AecDtlApplication.Database.GetFieldValueLong("NUM_NAILS")
    dNailDia = AecDtlApplication.Database.GetFieldValueDoubleUnitDep("NAIL_DIA")
    
    dblPnt(0) = 0#
    dblPnt(1) = 0#
    dblPnt(2) = 0#
    varPnt1 = dblPnt
    varPnt2 = dblPnt
    
    varPnt1(0) = -dFlange
    blkdef.AddLine varPnt1, varPnt2
    
    varPnt2 = varPnt1
    varPnt2(1) = varPnt2(1) + dGauge
    blkdef.AddLine varPnt1, varPnt2
    
    varPnt1 = varPnt2
    varPnt2(0) = varPnt2(0) + dFlange + dGauge
    blkdef.AddLine varPnt1, varPnt2
    
    varPnt1 = varPnt2
    varPnt2(1) = varPnt2(1) - dFlange * (2# / 3#)
    blkdef.AddLine varPnt1, varPnt2
    
    varPnt1 = varPnt2
    varPnt2(0) = varPnt2(0) - dGauge
    blkdef.AddLine varPnt1, varPnt2
    
    varPnt1 = varPnt2
    varPnt2(1) = 0#
    blkdef.AddLine varPnt1, varPnt2
    
    varPnt1 = dblPnt
    varPnt2 = dblPnt
    varPnt1(1) = dGauge - dFlange * (2# / 3#)
    varPnt2(1) = dGauge - dHeight + (dHeight * 0.15)
    blkdef.AddLine varPnt1, varPnt2
    
    varPnt1 = varPnt2
    varPnt2(0) = dGauge
    blkdef.AddLine varPnt1, varPnt2
    
    varPnt1 = varPnt2
    varPnt2(1) = dGauge - dFlange * (2# / 3#)
    blkdef.AddLine varPnt1, varPnt2
    
    varPnt1 = varPnt2
    varPnt2(0) = varPnt2(0) + dBase * (2# / 3#)
    blkdef.AddLine varPnt1, varPnt2
    
    varPnt1 = varPnt2
    varPnt2(0) = varPnt2(0) + dBase * (1# / 3#)
    varPnt2(1) = -dHeight
    blkdef.AddLine varPnt1, varPnt2
    
    varPnt1 = varPnt2
    varPnt2(1) = varPnt2(1) - dGauge
    blkdef.AddLine varPnt1, varPnt2
    
    varPnt1 = varPnt2
    varPnt2(0) = dGauge + dBase * 0.15
    blkdef.AddLine varPnt1, varPnt2
    
    varPnt1 = varPnt2
    varPnt2(1) = varPnt2(1) + dGauge
    blkdef.AddLine varPnt1, varPnt2
    
    varPnt1 = varPnt2
    varPnt2(0) = dGauge
    varPnt2(1) = dGauge - dHeight + (dHeight * 0.15)
    blkdef.AddLine varPnt1, varPnt2
    
    varPnt1(0) = dGauge + dBase * 0.15
    varPnt1(1) = -dHeight#
    varPnt2(0) = dBase + dGauge
    varPnt2(1) = -dHeight#
    AecDtlApplication.Recipe.SetEntityProperties "hide", blkdef.AddLine(varPnt1, varPnt2)
    
    For lngI = 1 To iNumNails
    
        Select Case lngI
            Case 1
                varPnt1 = dblPnt
                varPnt1(0) = dGauge + (dBase * 0.5)
                varPnt1(1) = -dHeight * 0.85 - dNailDia * 3#
                blkdef.AddCircle varPnt1, dNailDia
            Case 2
                varPnt1 = dblPnt
                varPnt1(0) = dGauge + (dBase * 0.5)
                varPnt1(1) = -dHeight * 0.85 + dNailDia * 3#
                blkdef.AddCircle varPnt1, dNailDia
            Case 3
                varPnt1 = dblPnt
                varPnt1(0) = dGauge + (dBase * 0.5) - dNailDia * 3#
                varPnt1(1) = -dHeight * 0.85
                blkdef.AddCircle varPnt1, dNailDia
            Case 4
                varPnt1 = dblPnt
                varPnt1(0) = dGauge + (dBase * 0.5) + dNailDia * 3#
                varPnt1(1) = -dHeight * 0.85
                blkdef.AddCircle varPnt1, dNailDia
            Case 5
                varPnt1 = dblPnt
                varPnt1(0) = dGauge + (dBase * 0.35)
                varPnt1(1) = -dHeight * 0.6 - dNailDia * 3#
                blkdef.AddCircle varPnt1, dNailDia
            Case 6
                varPnt1 = dblPnt
                varPnt1(0) = dGauge + (dBase * 0.35)
                varPnt1(1) = -dHeight * 0.6 + dNailDia * 3#
                blkdef.AddCircle varPnt1, dNailDia
            Case 7
                varPnt1 = dblPnt
                varPnt1(0) = dGauge + (dBase * 0.35) - dNailDia * 3#
                varPnt1(1) = -dHeight * 0.6
                blkdef.AddCircle varPnt1, dNailDia
            Case 8
                varPnt1 = dblPnt
                varPnt1(0) = dGauge + (dBase * 0.35) + dNailDia * 3#
                varPnt1(1) = -dHeight * 0.6
                blkdef.AddCircle varPnt1, dNailDia
        End Select
        
    Next lngI
    
    ' start the jig
    Dim status As AecDtlPromptStatus
    status = AecDtlApplication.jig.StampBlock(blkdef)

    ' return the status
    AecDtlApplication.Recipe.ReturnStatus = status

End Sub
Public Sub AecDtlRcpJHMJoistHangerSection()

    Dim dblPnt(0 To 2) As Double
    Dim blkdef As AcadBlock
    dblPnt(0) = 0#
    dblPnt(1) = 0#
    dblPnt(2) = 0#
    Set blkdef = ThisDrawing.Blocks.Add(dblPnt, "*U")
    
    Dim varEnt As Variant
    
    ' get the db values
    Dim dHeight As Double
    Dim dBase As Double
    Dim dFlange As Double
    Dim dGauge As Double
    Dim iNumNails As Integer
    Dim dNailDia As Double
    Dim dDepth As Double
    
    Dim varPnt1 As Variant
    Dim varPnt2 As Variant
    
    Dim lngI As Long
    
    dHeight = AecDtlApplication.Database.GetFieldValueDoubleUnitDep("HEIGHT")
    dBase = AecDtlApplication.Database.GetFieldValueDoubleUnitDep("BASE")
    dFlange = AecDtlApplication.Database.GetFieldValueDoubleUnitDep("FLANGE")
    dGauge = AecDtlApplication.Database.GetFieldValueDoubleUnitDep("DGAUGE")
    iNumNails = AecDtlApplication.Database.GetFieldValueLong("NUM_NAILS")
    dNailDia = AecDtlApplication.Database.GetFieldValueDoubleUnitDep("NAIL_DIA")
    dDepth = AecDtlApplication.Database.GetFieldValueDoubleUnitDep("DEPTH")
    
    dblPnt(0) = 0#
    dblPnt(1) = 0#
    dblPnt(2) = 0#
    varPnt1 = dblPnt
    varPnt2 = dblPnt
    
    varPnt1(0) = -dFlange
    blkdef.AddLine varPnt1, varPnt2
    
    varPnt2 = varPnt1
    varPnt2(1) = varPnt2(1) + dGauge
    blkdef.AddLine varPnt1, varPnt2
    
    varPnt1 = varPnt2
    varPnt2(0) = varPnt2(0) + dFlange + dGauge
    blkdef.AddLine varPnt1, varPnt2
    
    varPnt1 = varPnt2
    varPnt2(1) = varPnt2(1) - dHeight * 0.15
    blkdef.AddLine varPnt1, varPnt2
    
    varPnt1 = varPnt2
    varPnt2(0) = varPnt2(0) - dGauge
    blkdef.AddLine varPnt1, varPnt2
    
    varPnt1 = varPnt2
    varPnt2(1) = 0#
    blkdef.AddLine varPnt1, varPnt2
    
    varPnt1 = dblPnt
    varPnt2 = dblPnt
    
    varPnt1(0) = -dFlange
    varPnt1(1) = dGauge
    varPnt2 = varPnt1
    varPnt2(1) = varPnt2(1) + dGauge * 0.25
    blkdef.AddLine varPnt1, varPnt2
    
    varPnt1 = varPnt2
    varPnt2(0) = varPnt2(0) + dFlange + dGauge * 1.25
    blkdef.AddLine varPnt1, varPnt2

    varPnt1 = varPnt2
    varPnt2(1) = varPnt2(1) - dHeight * 0.1 - dGauge * 0.5
    blkdef.AddLine varPnt1, varPnt2

    varPnt1 = varPnt2
    varPnt2(0) = varPnt2(0) - dGauge * 0.25
    blkdef.AddLine varPnt1, varPnt2
    
    varPnt1 = dblPnt
    varPnt1(0) = dGauge
    varPnt1(1) = dGauge - dHeight * 0.15
    varPnt2 = varPnt1
    varPnt2(0) = varPnt2(0) + dDepth * 0.75
    blkdef.AddLine varPnt1, varPnt2
    
    varPnt1 = varPnt2
    varPnt2(1) = -dHeight + (dBase - dDepth) + dDepth * 0.75
    blkdef.AddLine varPnt1, varPnt2

    varPnt1 = varPnt2
    varPnt2(0) = varPnt2(0) + (dBase - dDepth) + dDepth * 0.25
    varPnt2(1) = varPnt2(1) - dDepth * 0.75
    blkdef.AddLine varPnt1, varPnt2

    varPnt1 = varPnt2
    varPnt2(1) = varPnt2(1) - (dBase - dDepth) - dGauge
    blkdef.AddLine varPnt1, varPnt2

    varPnt1 = varPnt2
    varPnt2(0) = varPnt2(0) - dDepth
    blkdef.AddLine varPnt1, varPnt2

    varPnt1 = varPnt2
    varPnt2(1) = varPnt2(1) + (dBase - dDepth) + dGauge
    blkdef.AddLine varPnt1, varPnt2

    varPnt1 = varPnt2
    varPnt2(0) = 0#
    varPnt2(1) = varPnt2(1) + (dBase - dDepth)
    blkdef.AddLine varPnt1, varPnt2

    varPnt1 = varPnt2
    varPnt2(0) = 0#
    varPnt2(1) = dGauge - dHeight * 0.15
    blkdef.AddLine varPnt1, varPnt2
    
    varPnt1(0) = dGauge + (dBase - dDepth)
    varPnt1(1) = -dHeight#
    varPnt2(0) = dBase + dGauge
    varPnt2(1) = -dHeight#
    AecDtlApplication.Recipe.SetEntityProperties "hide", blkdef.AddLine(varPnt1, varPnt2)
    
    For lngI = 1 To iNumNails

        Select Case lngI
            Case 1
                varPnt1 = dblPnt
                varPnt1(0) = dGauge + (dBase * 0.65)
                varPnt1(1) = -dHeight + dDepth * 0.45
                blkdef.AddCircle varPnt1, dNailDia
            Case 2
                varPnt1 = dblPnt
                varPnt1(0) = dGauge + (dDepth * 0.5)
                varPnt1(1) = -dHeight + dDepth * 1#
                blkdef.AddCircle varPnt1, dNailDia
        End Select

    Next lngI
    
    ' start the jig
    Dim status As AecDtlPromptStatus
    status = AecDtlApplication.jig.StampBlock(blkdef)

    ' return the status
    AecDtlApplication.Recipe.ReturnStatus = status

End Sub
Public Sub AecDtlRcpLBVJoistHangerSection()

    Dim dblPnt(0 To 2) As Double
    Dim blkdef As AcadBlock
    dblPnt(0) = 0#
    dblPnt(1) = 0#
    dblPnt(2) = 0#
    Set blkdef = ThisDrawing.Blocks.Add(dblPnt, "*U")
    
    Dim varEnt As Variant
    
    ' get the db values
    Dim dHeight As Double
    Dim dBase As Double
    Dim dFlange As Double
    Dim dGauge As Double
    Dim dNailSpace As Double
    
    Dim varPnt1 As Variant
    Dim varPnt2 As Variant
    Dim varPnt3 As Variant
    Dim varPnt4 As Variant
    
    Dim lngI As Long
    
    dHeight = AecDtlApplication.Database.GetFieldValueDoubleUnitDep("HEIGHT")
    dBase = AecDtlApplication.Database.GetFieldValueDoubleUnitDep("BASE")
    dFlange = AecDtlApplication.Database.GetFieldValueDoubleUnitDep("FLANGE")
    dGauge = AecDtlApplication.Database.GetFieldValueDoubleUnitDep("DGAGE")
    
    dNailSpace = AecDtlApplication.Recipe.GetDataValueDoubleUnitDep("boundary", "NailSpace")
    
    dblPnt(0) = 0#
    dblPnt(1) = 0#
    dblPnt(2) = 0#
    varPnt1 = dblPnt
    varPnt2 = dblPnt
    
    varPnt1(0) = -dFlange
    blkdef.AddLine varPnt1, varPnt2
    
    varPnt2 = varPnt1
    varPnt2(1) = varPnt2(1) + dGauge
    blkdef.AddLine varPnt1, varPnt2
    
    varPnt1 = varPnt2
    varPnt2(0) = varPnt2(0) + dFlange + dGauge
    blkdef.AddLine varPnt1, varPnt2
    
    varPnt1 = varPnt2
    varPnt2(1) = varPnt2(1) - dHeight - dGauge
    blkdef.AddLine varPnt1, varPnt2
    
    varPnt1 = varPnt2
    varPnt2(0) = varPnt2(0) - dGauge
    blkdef.AddLine varPnt1, varPnt2
    
    varPnt1 = varPnt2
    varPnt2(1) = 0#
    blkdef.AddLine varPnt1, varPnt2
    
    varPnt1 = dblPnt
    varPnt1(0) = dGauge
    varPnt1(1) = dGauge
    varPnt4 = varPnt1
    varPnt2 = dblPnt
    varPnt2(0) = dGauge + dBase
    varPnt2(1) = varPnt2(1) - dHeight
    varPnt3 = varPnt2
    blkdef.AddLine varPnt1, varPnt2
    
    varPnt1 = varPnt2
    varPnt2(1) = varPnt2(1) - dGauge
    blkdef.AddLine varPnt1, varPnt2
    
    varPnt1 = varPnt2
    varPnt2(0) = dGauge + dBase - dBase
    blkdef.AddLine varPnt1, varPnt2
    
    varPnt1 = varPnt2
    varPnt2(1) = 0#
    blkdef.AddLine varPnt1, varPnt2
    
    varPnt1(0) = dGauge
    varPnt1(1) = -dHeight#
    varPnt2(0) = dBase + dGauge
    varPnt2(1) = -dHeight#
    AecDtlApplication.Recipe.SetEntityProperties "hide", blkdef.AddLine(varPnt1, varPnt2)
    
    varPnt1(0) = dGauge + (dBase * 0.6)
    varPnt1(1) = -(dHeight * 0.8)
    For lngI = 1 To 2
        blkdef.AddCircle varPnt1, 4#
        varPnt1 = CDLPolar(varPnt1, CDLAngle(varPnt3, varPnt4), dNailSpace)
    Next lngI
    
    ' start the jig
    Dim status As AecDtlPromptStatus
    status = AecDtlApplication.jig.StampBlock(blkdef)

    ' return the status
    AecDtlApplication.Recipe.ReturnStatus = status

End Sub
Public Sub AecDtlRcpWPJoistHangerSection()

    Dim dblPnt(0 To 2) As Double
    Dim blkdef As AcadBlock
    dblPnt(0) = 0#
    dblPnt(1) = 0#
    dblPnt(2) = 0#
    Set blkdef = ThisDrawing.Blocks.Add(dblPnt, "*U")
    
    Dim varEnt As Variant
    
    ' get the db values
    Dim dHeight As Double
    Dim dBase As Double
    Dim dFlange As Double
    Dim dGauge As Double
    Dim iNumNails As Integer
    Dim dNailDia As Double
    Dim dNailSpace As Double
    
    Dim varPnt1 As Variant
    Dim varPnt2 As Variant
    
    Dim lngI As Long
    
    dHeight = AecDtlApplication.Database.GetFieldValueDoubleUnitDep("HEIGHT")
    dBase = AecDtlApplication.Database.GetFieldValueDoubleUnitDep("BASE")
    dFlange = AecDtlApplication.Database.GetFieldValueDoubleUnitDep("FLANGE")
    dGauge = AecDtlApplication.Database.GetFieldValueDoubleUnitDep("DGAGE")
    iNumNails = AecDtlApplication.Database.GetFieldValueLong("NUM_NAILS")
    dNailDia = AecDtlApplication.Database.GetFieldValueDoubleUnitDep("NAIL_DIA")
    
    dNailSpace = AecDtlApplication.Recipe.GetDataValueDoubleUnitDep("boundary", "NailSpace")
    
    dblPnt(0) = 0#
    dblPnt(1) = 0#
    dblPnt(2) = 0#
    varPnt1 = dblPnt
    varPnt2 = dblPnt
    
    varPnt1(0) = -dFlange
    blkdef.AddLine varPnt1, varPnt2
    
    varPnt2 = varPnt1
    varPnt2(1) = varPnt2(1) + dGauge
    blkdef.AddLine varPnt1, varPnt2
    
    varPnt1 = varPnt2
    varPnt2(0) = varPnt2(0) + dFlange + dGauge
    blkdef.AddLine varPnt1, varPnt2
    
    varPnt1 = varPnt2
    varPnt2(1) = varPnt2(1) - dFlange
    blkdef.AddLine varPnt1, varPnt2
    
    varPnt1 = varPnt2
    varPnt2(0) = varPnt2(0) - dGauge
    blkdef.AddLine varPnt1, varPnt2
    
    varPnt1 = varPnt2
    varPnt2(1) = 0#
    blkdef.AddLine varPnt1, varPnt2
    
    varPnt1 = dblPnt
    varPnt1(0) = dGauge
    varPnt2 = dblPnt
    varPnt2(0) = dGauge + dBase
    blkdef.AddLine varPnt1, varPnt2
    
    varPnt1 = varPnt2
    varPnt2(1) = varPnt2(1) - dHeight - dGauge
    blkdef.AddLine varPnt1, varPnt2
    
    varPnt1 = varPnt2
    varPnt2(0) = varPnt2(0) - dBase
    blkdef.AddLine varPnt1, varPnt2
    
    varPnt1 = varPnt2
    varPnt2(1) = 0#
    blkdef.AddLine varPnt1, varPnt2
    
    varPnt1(0) = dGauge
    varPnt1(1) = -dHeight#
    varPnt2(0) = dBase + dGauge
    varPnt2(1) = -dHeight#
    AecDtlApplication.Recipe.SetEntityProperties "hide", blkdef.AddLine(varPnt1, varPnt2)
    
    varPnt1(0) = dGauge + (dBase * 0.75)
    varPnt1(1) = -(dHeight * 0.7)
    For lngI = 1 To iNumNails
        blkdef.AddCircle varPnt1, dNailDia
        varPnt1(1) = varPnt1(1) + dNailSpace
    Next lngI
    
    ' start the jig
    Dim status As AecDtlPromptStatus
    status = AecDtlApplication.jig.StampBlock(blkdef)

    ' return the status
    AecDtlApplication.Recipe.ReturnStatus = status

End Sub
Public Sub AecDtlRcpGLTVJoistHangerSection()

    Dim dblPnt(0 To 2) As Double
    Dim blkdef As AcadBlock
    dblPnt(0) = 0#
    dblPnt(1) = 0#
    dblPnt(2) = 0#
    Set blkdef = ThisDrawing.Blocks.Add(dblPnt, "*U")
    
    Dim varEnt As Variant
    
    ' get the db values
    Dim dHeight As Double
    Dim dBase As Double
    Dim dFlange As Double
    Dim dVFlange As Double
    Dim dGauge As Double
    Dim iNumNails As Integer
    Dim dNailDia As Double
    Dim dNailSpace As Double
    Dim lngPos As Long
    
    Dim varPnt1 As Variant
    Dim varPnt2 As Variant
    
    Dim lngI As Long
    
    dHeight = AecDtlApplication.Database.GetFieldValueDoubleUnitDep("HEIGHT")
    dBase = AecDtlApplication.Database.GetFieldValueDoubleUnitDep("BASE")
    dFlange = AecDtlApplication.Database.GetFieldValueDoubleUnitDep("FLANGE")
    dVFlange = AecDtlApplication.Database.GetFieldValueDoubleUnitDep("VFLANGE")
    dGauge = AecDtlApplication.Database.GetFieldValueDoubleUnitDep("DGAGE")
    iNumNails = AecDtlApplication.Database.GetFieldValueLong("NUM_NAILS")
    dNailDia = AecDtlApplication.Database.GetFieldValueDoubleUnitDep("NAIL_DIA")
    
    dNailSpace = AecDtlApplication.Recipe.GetDataValueDoubleUnitDep("boundary", "NailSpace")
    
    dblPnt(0) = 0#
    dblPnt(1) = 0#
    dblPnt(2) = 0#
    varPnt1 = dblPnt
    varPnt2 = dblPnt
    
    varPnt1(0) = -dFlange
    blkdef.AddLine varPnt1, varPnt2
    
    varPnt2 = varPnt1
    varPnt2(1) = varPnt2(1) + dGauge
    blkdef.AddLine varPnt1, varPnt2
    
    varPnt1 = varPnt2
    varPnt2(0) = varPnt2(0) + dFlange + dGauge
    blkdef.AddLine varPnt1, varPnt2
    
    varPnt1 = varPnt2
    varPnt2(1) = varPnt2(1) - dVFlange
    blkdef.AddLine varPnt1, varPnt2
    
    varPnt1 = varPnt2
    varPnt2(0) = varPnt2(0) - dGauge
    blkdef.AddLine varPnt1, varPnt2
    
    varPnt1 = varPnt2
    varPnt2(1) = 0#
    blkdef.AddLine varPnt1, varPnt2
    
    varPnt1 = dblPnt
    varPnt1(0) = dGauge
    varPnt2 = dblPnt
    varPnt2(0) = dGauge + dBase
    blkdef.AddLine varPnt1, varPnt2
    
    varPnt1 = varPnt2
    varPnt2(1) = varPnt2(1) - dHeight - dGauge
    blkdef.AddLine varPnt1, varPnt2
    
    varPnt1 = varPnt2
    varPnt2(0) = varPnt2(0) - dBase
    blkdef.AddLine varPnt1, varPnt2
    
    varPnt1 = varPnt2
    varPnt2(1) = 0#
    blkdef.AddLine varPnt1, varPnt2
    
    varPnt1(0) = dGauge
    varPnt1(1) = -dHeight#
    varPnt2(0) = dBase + dGauge
    varPnt2(1) = -dHeight#
    AecDtlApplication.Recipe.SetEntityProperties "hide", blkdef.AddLine(varPnt1, varPnt2)
    
    varPnt1(0) = dGauge + (dBase * 0.75)
    varPnt1(1) = -(dHeight * 0.7)
    lngPos = -1
    For lngI = 1 To iNumNails
        blkdef.AddCircle varPnt1, dNailDia
        varPnt1(1) = varPnt1(1) + dNailSpace
        varPnt1(0) = varPnt1(0) + dBase * 0.15 * lngPos
        lngPos = -lngPos
    Next lngI
    
    ' start the jig
    Dim status As AecDtlPromptStatus
    status = AecDtlApplication.jig.StampBlock(blkdef)

    ' return the status
    AecDtlApplication.Recipe.ReturnStatus = status

End Sub
Public Sub AecDtlRcpColdFormedZeeSection()

    Dim dblPnt(0 To 2) As Double
    Dim blkdef As AcadBlock
    dblPnt(0) = 0#
    dblPnt(1) = 0#
    dblPnt(2) = 0#
    Set blkdef = ThisDrawing.Blocks.Add(dblPnt, "*U")
    
    ' get the db values
    Dim dDepth As Double
    Dim dTF As Double
    Dim dBF As Double
    Dim dThick As Double
    Dim dTL As Double
    Dim dBL As Double
    
    dDepth = AecDtlApplication.Database.GetFieldValueDoubleUnitDep("DEPTH")
    dTF = AecDtlApplication.Database.GetFieldValueDoubleUnitDep("TOPFLANGE")
    dBF = AecDtlApplication.Database.GetFieldValueDoubleUnitDep("BOTTOMFLANGE")
    dThick = AecDtlApplication.Database.GetFieldValueDoubleUnitDep("THICKNESS")
    dTL = AecDtlApplication.Database.GetFieldValueDoubleUnitDep("TOPLIP")
    dBL = AecDtlApplication.Database.GetFieldValueDoubleUnitDep("BOTTOMLIP")
    
    Dim varPnt1 As Variant
    Dim varPnt2 As Variant
    
    varPnt1 = dblPnt
    varPnt1(1) = dThick
    varPnt2 = dblPnt
    varPnt2(1) = dDepth - dThick
    blkdef.AddLine varPnt1, varPnt2
    
    varPnt1 = varPnt2
    varPnt2(0) = varPnt2(0) + dTF - dThick * 2#
    blkdef.AddLine varPnt1, varPnt2
    
    varPnt1 = varPnt2
    varPnt2(1) = varPnt2(1) - dTL + dThick
    blkdef.AddLine varPnt1, varPnt2
        
    varPnt1 = varPnt2
    varPnt2(0) = varPnt2(0) + dThick
    blkdef.AddLine varPnt1, varPnt2
        
    varPnt1 = varPnt2
    varPnt2(1) = varPnt2(1) + dTL - dThick
    blkdef.AddLine varPnt1, varPnt2
        
    varPnt1 = varPnt2
    varPnt1(0) = varPnt1(0) - dThick
    blkdef.AddArc varPnt1, dThick, 0#, 90# * DegToRad
        
    varPnt2(0) = varPnt2(0) - dThick
    varPnt2(1) = varPnt2(1) + dThick
        
    varPnt1 = varPnt2
    varPnt2(0) = varPnt2(0) - dTF + dThick * 2#
    blkdef.AddLine varPnt1, varPnt2
        
    varPnt1 = varPnt2
    varPnt1(1) = varPnt1(1) - dThick
    blkdef.AddArc varPnt1, dThick, 90# * DegToRad, 180# * DegToRad
        
    varPnt2(0) = varPnt2(0) - dThick
    varPnt2(1) = varPnt2(1) - dThick
    
    varPnt1 = varPnt2
    varPnt2(1) = varPnt2(1) - dDepth + dThick * 2#
    blkdef.AddLine varPnt1, varPnt2
    
    varPnt1 = varPnt2
    varPnt2(0) = varPnt2(0) - dBF + dThick * 2#
    blkdef.AddLine varPnt1, varPnt2
    
    varPnt1 = varPnt2
    varPnt2(1) = varPnt2(1) + dBL - dThick
    blkdef.AddLine varPnt1, varPnt2
    
    varPnt1 = varPnt2
    varPnt2(0) = varPnt2(0) - dThick
    blkdef.AddLine varPnt1, varPnt2
    
    varPnt1 = varPnt2
    varPnt2(1) = varPnt2(1) - dBL + dThick
    blkdef.AddLine varPnt1, varPnt2
    
    varPnt1 = varPnt2
    varPnt1(0) = varPnt1(0) + dThick
    blkdef.AddArc varPnt1, dThick, 180# * DegToRad, 270# * DegToRad
    
    varPnt2(0) = varPnt2(0) + dThick
    varPnt2(1) = varPnt2(1) - dThick
    
    varPnt1 = varPnt2
    varPnt2(0) = varPnt2(0) + dBF - dThick * 2#
    blkdef.AddLine varPnt1, varPnt2
    
    varPnt1 = varPnt2
    varPnt1(1) = varPnt1(1) + dThick
    blkdef.AddArc varPnt1, dThick, 270# * DegToRad, 0#

    ' start the jig
    Dim status As AecDtlPromptStatus
    status = AecDtlApplication.jig.StampBlock(blkdef)

    ' return the status
    AecDtlApplication.Recipe.ReturnStatus = status

End Sub
Public Sub AecDtlRcpColdFormedZeeElevation()

    Dim dblPnt(0 To 2) As Double
    Dim blkdef As AcadBlock
    dblPnt(0) = 0#
    dblPnt(1) = 0#
    dblPnt(2) = 0#
    Set blkdef = ThisDrawing.Blocks.Add(dblPnt, "*U")
    
    ' get the db values
    Dim dDepth As Double
    Dim dTF As Double
    Dim dBF As Double
    Dim dThick As Double
    Dim dTL As Double
    Dim dBL As Double
    
    dDepth = AecDtlApplication.Database.GetFieldValueDoubleUnitDep("DEPTH")
    dTF = AecDtlApplication.Database.GetFieldValueDoubleUnitDep("TOPFLANGE")
    dBF = AecDtlApplication.Database.GetFieldValueDoubleUnitDep("BOTTOMFLANGE")
    dThick = AecDtlApplication.Database.GetFieldValueDoubleUnitDep("THICKNESS")
    dTL = AecDtlApplication.Database.GetFieldValueDoubleUnitDep("TOPLIP")
    dBL = AecDtlApplication.Database.GetFieldValueDoubleUnitDep("BOTTOMLIP")
    
    Dim varPnt1 As Variant
    Dim varPnt2 As Variant
    
    varPnt1 = dblPnt
    varPnt2 = dblPnt
    varPnt2(0) = 1#
    AecDtlApplication.Recipe.SetEntityProperties "boundary", blkdef.AddLine(varPnt1, varPnt2)
    
    varPnt1 = varPnt2
    varPnt2(1) = varPnt2(1) + dDepth
    AecDtlApplication.Recipe.SetEntityProperties "boundary", blkdef.AddLine(varPnt1, varPnt2)
    
    varPnt1 = varPnt2
    varPnt2(0#) = 0#
    AecDtlApplication.Recipe.SetEntityProperties "boundary", blkdef.AddLine(varPnt1, varPnt2)
        
    varPnt1 = varPnt2
    varPnt2(1) = 0#
    AecDtlApplication.Recipe.SetEntityProperties "boundary", blkdef.AddLine(varPnt1, varPnt2)
        
    varPnt1 = dblPnt
    varPnt1(1) = dDepth - dTL
    varPnt2 = dblPnt
    varPnt2(0) = 1#
    varPnt2(1) = dDepth - dTL
    AecDtlApplication.Recipe.SetEntityProperties "boundary", blkdef.AddLine(varPnt1, varPnt2)
        
    varPnt1 = dblPnt
    varPnt1(1) = dDepth - dThick
    varPnt2 = dblPnt
    varPnt2(0) = 1#
    varPnt2(1) = dDepth - dThick
    AecDtlApplication.Recipe.SetEntityProperties "hidden", blkdef.AddLine(varPnt1, varPnt2)
        
    varPnt1 = dblPnt
    varPnt1(1) = dThick
    varPnt2 = dblPnt
    varPnt2(0) = 1#
    varPnt2(1) = dThick
    AecDtlApplication.Recipe.SetEntityProperties "hidden", blkdef.AddLine(varPnt1, varPnt2)
        
    varPnt1 = dblPnt
    varPnt1(1) = dBL
    varPnt2 = dblPnt
    varPnt2(0) = 1#
    varPnt2(1) = dBL
    AecDtlApplication.Recipe.SetEntityProperties "hidden", blkdef.AddLine(varPnt1, varPnt2)
        
    ' start the jig
    Dim status As AecDtlPromptStatus
    status = AecDtlApplication.jig.StretchBlock(blkdef)

    ' return the status
    AecDtlApplication.Recipe.ReturnStatus = status

End Sub
Public Sub AecDtlRcpColdFormedZeePlan()

    Dim dblPnt(0 To 2) As Double
    Dim blkdef As AcadBlock
    dblPnt(0) = 0#
    dblPnt(1) = 0#
    dblPnt(2) = 0#
    Set blkdef = ThisDrawing.Blocks.Add(dblPnt, "*U")
    
    ' get the db values
    Dim dDepth As Double
    Dim dTF As Double
    Dim dBF As Double
    Dim dThick As Double
    Dim dTL As Double
    Dim dBL As Double
    
    dDepth = AecDtlApplication.Database.GetFieldValueDoubleUnitDep("DEPTH")
    dTF = AecDtlApplication.Database.GetFieldValueDoubleUnitDep("TOPFLANGE")
    dBF = AecDtlApplication.Database.GetFieldValueDoubleUnitDep("BOTTOMFLANGE")
    dThick = AecDtlApplication.Database.GetFieldValueDoubleUnitDep("THICKNESS")
    dTL = AecDtlApplication.Database.GetFieldValueDoubleUnitDep("TOPLIP")
    dBL = AecDtlApplication.Database.GetFieldValueDoubleUnitDep("BOTTOMLIP")
    
    Dim varPnt1 As Variant
    Dim varPnt2 As Variant
    
    varPnt1 = dblPnt
    varPnt2 = dblPnt
    varPnt2(0) = 1#
    AecDtlApplication.Recipe.SetEntityProperties "boundary", blkdef.AddLine(varPnt1, varPnt2)
    
    varPnt1 = varPnt2
    varPnt2(1) = varPnt2(1) + dTF - dThick + dBF
    AecDtlApplication.Recipe.SetEntityProperties "boundary", blkdef.AddLine(varPnt1, varPnt2)
    
    varPnt1 = varPnt2
    varPnt2(0#) = 0#
    AecDtlApplication.Recipe.SetEntityProperties "boundary", blkdef.AddLine(varPnt1, varPnt2)
        
    varPnt1 = varPnt2
    varPnt2(1) = 0#
    AecDtlApplication.Recipe.SetEntityProperties "boundary", blkdef.AddLine(varPnt1, varPnt2)
        
    varPnt1 = dblPnt
    varPnt1(1) = dTF
    varPnt2 = dblPnt
    varPnt2(0) = 1#
    varPnt2(1) = dTF
    AecDtlApplication.Recipe.SetEntityProperties "boundary", blkdef.AddLine(varPnt1, varPnt2)

    varPnt1 = dblPnt
    varPnt1(1) = dTF - dThick
    varPnt2 = dblPnt
    varPnt2(0) = 1#
    varPnt2(1) = dTF - dThick
    AecDtlApplication.Recipe.SetEntityProperties "hidden", blkdef.AddLine(varPnt1, varPnt2)

    varPnt1 = dblPnt
    varPnt1(1) = varPnt1(1) + dTF - dThick * 2# + dBF
    varPnt2 = dblPnt
    varPnt2(0) = 1#
    varPnt2(1) = varPnt2(1) + dTF - dThick * 2# + dBF
    AecDtlApplication.Recipe.SetEntityProperties "boundary", blkdef.AddLine(varPnt1, varPnt2)

    varPnt1 = dblPnt
    varPnt1(1) = dThick
    varPnt2 = dblPnt
    varPnt2(0) = 1#
    varPnt2(1) = dThick
    AecDtlApplication.Recipe.SetEntityProperties "hidden", blkdef.AddLine(varPnt1, varPnt2)

    ' start the jig
    Dim status As AecDtlPromptStatus
    status = AecDtlApplication.jig.StretchBlock(blkdef)

    ' return the status
    AecDtlApplication.Recipe.ReturnStatus = status

End Sub
Public Sub AecDtlMetalJoistOpenWebSection()

    Dim dblPnt(0 To 2) As Double
    Dim blkdef As AcadBlock
    dblPnt(0) = 0#
    dblPnt(1) = 0#
    dblPnt(2) = 0#
    Set blkdef = ThisDrawing.Blocks.Add(dblPnt, "*U")
    
    ' get the db values
    Dim dDepth As Double
    Dim dA As Double
    Dim dB As Double
    Dim dC As Double
    Dim dD As Double
    Dim dE As Double
    Dim dT As Double
    
    dDepth = AecDtlApplication.Database.GetFieldValueDoubleUnitDep("DEPTH")
    dA = AecDtlApplication.Database.GetFieldValueDoubleUnitDep("DIM_A")
    dB = AecDtlApplication.Database.GetFieldValueDoubleUnitDep("DIM_B")
    dC = AecDtlApplication.Database.GetFieldValueDoubleUnitDep("DIM_C")
    dD = AecDtlApplication.Database.GetFieldValueDoubleUnitDep("DIM_D")
    dE = AecDtlApplication.Database.GetFieldValueDoubleUnitDep("DIM_E")
    dT = AecDtlApplication.Database.GetFieldValueDoubleUnitDep("DIM_T")
    
    Dim varPnt1 As Variant
    Dim varPnt2 As Variant
    Dim varPnt3 As Variant
    Dim varPnt4 As Variant
    
    varPnt3 = dblPnt
    varPnt3(1) = -dDepth / 2#
    varPnt4 = varPnt3
    varPnt4(0) = 1#
    
    If dE <> 0# Then
        
        varPnt1 = dblPnt
        varPnt1(0) = -dA / 2#
        varPnt1(1) = -dE
        varPnt2 = dblPnt
        varPnt2(0) = -dA / 2#
        varPnt2(1) = -dT
        blkdef.AddLine(varPnt1, varPnt2).Mirror varPnt3, varPnt4
        
        varPnt1 = varPnt2
        varPnt1(0) = varPnt1(0) + dT
        blkdef.AddArc(varPnt1, dT, 90# * DegToRad, 180# * DegToRad).Mirror varPnt3, varPnt4
        
        varPnt2(0) = varPnt2(0) + dT
        varPnt2(1) = varPnt2(1) + dT
        
    Else
    
        varPnt2 = dblPnt
        varPnt2(0) = -dA / 2#
    
    End If
    
    varPnt1 = varPnt2
    varPnt2(0) = -dC / 2# - dT
    blkdef.AddLine(varPnt1, varPnt2).Mirror varPnt3, varPnt4
    
    varPnt1 = varPnt2
    varPnt1(1) = varPnt1(1) - dT
    blkdef.AddArc(varPnt1, dT, 0#, 90# * DegToRad).Mirror varPnt3, varPnt4
        
    varPnt2(0) = varPnt2(0) + dT
    varPnt2(1) = varPnt2(1) - dT
    
    varPnt1 = varPnt2
    varPnt2(1) = -dD + dT
    blkdef.AddLine(varPnt1, varPnt2).Mirror varPnt3, varPnt4
    
    varPnt1 = varPnt2
    varPnt2(0) = varPnt2(0) + dC
    blkdef.AddLine(varPnt1, varPnt2).Mirror varPnt3, varPnt4
    
    varPnt1 = varPnt2
    varPnt2(1) = -dT
    blkdef.AddLine(varPnt1, varPnt2).Mirror varPnt3, varPnt4
    
    varPnt1 = varPnt2
    varPnt1(0) = varPnt1(0) + dT
    blkdef.AddArc(varPnt1, dT, 90# * DegToRad, 180# * DegToRad).Mirror varPnt3, varPnt4
        
    varPnt2(0) = varPnt2(0) + dT
    varPnt2(1) = varPnt2(1) + dT
    
    If dE <> 0# Then
        
        varPnt1 = varPnt2
        varPnt2(0) = varPnt1(0) + dB - dT * 2#
        blkdef.AddLine(varPnt1, varPnt2).Mirror varPnt3, varPnt4
        
        varPnt1 = varPnt2
        varPnt1(1) = varPnt1(1) - dT
        blkdef.AddArc(varPnt1, dT, 0#, 90# * DegToRad).Mirror varPnt3, varPnt4
            
        varPnt2(0) = varPnt2(0) + dT
        varPnt2(1) = varPnt2(1) - dT
        
        varPnt1 = varPnt2
        varPnt2(1) = -dE
        blkdef.AddLine(varPnt1, varPnt2).Mirror varPnt3, varPnt4
    
        varPnt1 = varPnt2
        varPnt2(0) = varPnt2(0) - dT
        blkdef.AddLine(varPnt1, varPnt2).Mirror varPnt3, varPnt4
    
        varPnt1 = varPnt2
        varPnt2(1) = -dT
        blkdef.AddLine(varPnt1, varPnt2).Mirror varPnt3, varPnt4
    
    Else
    
        varPnt1 = varPnt2
        varPnt2(0) = varPnt1(0) + dB - dT
        blkdef.AddLine(varPnt1, varPnt2).Mirror varPnt3, varPnt4
        
        varPnt1 = varPnt2
        varPnt2(1) = -dT
        blkdef.AddLine(varPnt1, varPnt2).Mirror varPnt3, varPnt4
    
    End If
    
    varPnt1 = varPnt2
    varPnt2(0) = dC / 2# + dT
    blkdef.AddLine(varPnt1, varPnt2).Mirror varPnt3, varPnt4
    
    varPnt1 = varPnt2
    varPnt2(1) = -dD + dT
    blkdef.AddLine(varPnt1, varPnt2).Mirror varPnt3, varPnt4
        
    varPnt1 = varPnt2
    varPnt1(0) = varPnt1(0) - dT
    blkdef.AddArc(varPnt1, dT, 270# * DegToRad, 0# * DegToRad).Mirror varPnt3, varPnt4
        
    varPnt2(0) = varPnt2(0) - dT
    varPnt2(1) = varPnt2(1) - dT
        
    varPnt1 = varPnt2
    varPnt2(0) = -dC / 2#
    blkdef.AddLine(varPnt1, varPnt2).Mirror varPnt3, varPnt4
    
    varPnt1 = varPnt2
    varPnt1(1) = varPnt1(1) + dT
    blkdef.AddArc(varPnt1, dT, 180# * DegToRad, 270# * DegToRad).Mirror varPnt3, varPnt4
        
    varPnt2(0) = varPnt2(0) - dT
    varPnt2(1) = varPnt2(1) + dT
    
    varPnt1 = varPnt2
    varPnt2(1) = -dT
    blkdef.AddLine(varPnt1, varPnt2).Mirror varPnt3, varPnt4
    
    If dE <> 0# Then
        
        varPnt1 = varPnt2
        varPnt2(0) = -dA / 2# + dT
        blkdef.AddLine(varPnt1, varPnt2).Mirror varPnt3, varPnt4
        
        varPnt1 = varPnt2
        varPnt2(1) = varPnt1(1) - dE + dT
        blkdef.AddLine(varPnt1, varPnt2).Mirror varPnt3, varPnt4
        
        varPnt1 = varPnt2
        varPnt2(0) = -dA / 2#
        blkdef.AddLine(varPnt1, varPnt2).Mirror varPnt3, varPnt4
        
    Else
    
        varPnt1 = varPnt2
        varPnt2(0) = -dA / 2#
        blkdef.AddLine(varPnt1, varPnt2).Mirror varPnt3, varPnt4

        varPnt1 = varPnt2
        varPnt2(1) = 0#
        blkdef.AddLine(varPnt1, varPnt2).Mirror varPnt3, varPnt4
    
    End If
    
    varPnt1(0) = -dC / 2# + dT
    varPnt1(1) = -dD
    varPnt2 = varPnt1
    varPnt1(1) = -dDepth + dD
    blkdef.AddLine varPnt1, varPnt2
    
    varPnt1(0) = dC / 2# - dT
    varPnt1(1) = -dD
    varPnt2 = varPnt1
    varPnt1(1) = -dDepth + dD
    blkdef.AddLine varPnt1, varPnt2
    
    ' start the jig
    Dim status As AecDtlPromptStatus
    status = AecDtlApplication.jig.StampBlock(blkdef)

    ' return the status
    AecDtlApplication.Recipe.ReturnStatus = status

End Sub
Public Sub AecDtlMetalJoistOpenWebPlan()

    Dim dblPnt(0 To 2) As Double
    Dim blkdef As AcadBlock
    dblPnt(0) = 0#
    dblPnt(1) = 0#
    dblPnt(2) = 0#
    Set blkdef = ThisDrawing.Blocks.Add(dblPnt, "*U")
    
    ' get the db values
    Dim dDepth As Double
    Dim dA As Double
    Dim dB As Double
    Dim dC As Double
    Dim dD As Double
    Dim dE As Double
    Dim dT As Double
    
    dDepth = AecDtlApplication.Database.GetFieldValueDoubleUnitDep("DEPTH")
    dA = AecDtlApplication.Database.GetFieldValueDoubleUnitDep("DIM_A")
    dB = AecDtlApplication.Database.GetFieldValueDoubleUnitDep("DIM_B")
    dC = AecDtlApplication.Database.GetFieldValueDoubleUnitDep("DIM_C")
    dD = AecDtlApplication.Database.GetFieldValueDoubleUnitDep("DIM_D")
    dE = AecDtlApplication.Database.GetFieldValueDoubleUnitDep("DIM_E")
    dT = AecDtlApplication.Database.GetFieldValueDoubleUnitDep("DIM_T")
    
    Dim varPnt1 As Variant
    Dim varPnt2 As Variant
    
    varPnt1 = dblPnt
    varPnt1(1) = -dA / 2#
    varPnt2 = dblPnt
    varPnt2(0) = 1#
    varPnt2(1) = -dA / 2#
    AecDtlApplication.Recipe.SetEntityProperties "boundary", blkdef.AddLine(varPnt1, varPnt2)
    
    varPnt1 = varPnt2
    varPnt2(1) = varPnt2(1) + dA
    AecDtlApplication.Recipe.SetEntityProperties "boundary", blkdef.AddLine(varPnt1, varPnt2)
    
    varPnt1 = varPnt2
    varPnt2(0#) = 0#
    AecDtlApplication.Recipe.SetEntityProperties "boundary", blkdef.AddLine(varPnt1, varPnt2)
        
    varPnt1 = varPnt2
    varPnt2(1) = -dA / 2#
    AecDtlApplication.Recipe.SetEntityProperties "boundary", blkdef.AddLine(varPnt1, varPnt2)
    
    If dE <> 0# Then
        
        varPnt1 = dblPnt
        varPnt1(1) = -dA / 2# + dT
        varPnt2 = dblPnt
        varPnt2(0) = 1#
        varPnt2(1) = -dA / 2# + dT
        AecDtlApplication.Recipe.SetEntityProperties "hidden", blkdef.AddLine(varPnt1, varPnt2)
        
        varPnt1 = dblPnt
        varPnt1(1) = dA / 2# - dT
        varPnt2 = dblPnt
        varPnt2(0) = 1#
        varPnt2(1) = dA / 2# - dT
        AecDtlApplication.Recipe.SetEntityProperties "hidden", blkdef.AddLine(varPnt1, varPnt2)
        
    End If
        
    varPnt1 = dblPnt
    varPnt1(1) = -dC / 2#
    varPnt2 = dblPnt
    varPnt2(0) = 1#
    varPnt2(1) = -dC / 2#
    AecDtlApplication.Recipe.SetEntityProperties "boundary", blkdef.AddLine(varPnt1, varPnt2)
        
    varPnt1 = dblPnt
    varPnt1(1) = dC / 2#
    varPnt2 = dblPnt
    varPnt2(0) = 1#
    varPnt2(1) = dC / 2#
    AecDtlApplication.Recipe.SetEntityProperties "boundary", blkdef.AddLine(varPnt1, varPnt2)
        
    varPnt1 = dblPnt
    varPnt1(1) = -dC / 2# - dT
    varPnt2 = dblPnt
    varPnt2(0) = 1#
    varPnt2(1) = -dC / 2# - dT
    AecDtlApplication.Recipe.SetEntityProperties "hidden", blkdef.AddLine(varPnt1, varPnt2)
        
    varPnt1 = dblPnt
    varPnt1(1) = dC / 2# + dT
    varPnt2 = dblPnt
    varPnt2(0) = 1#
    varPnt2(1) = dC / 2# + dT
    AecDtlApplication.Recipe.SetEntityProperties "hidden", blkdef.AddLine(varPnt1, varPnt2)
        
    varPnt1 = dblPnt
    varPnt1(1) = -dC / 2# + dT
    varPnt2 = dblPnt
    varPnt2(0) = 1#
    varPnt2(1) = -dC / 2# + dT
    AecDtlApplication.Recipe.SetEntityProperties "hidden", blkdef.AddLine(varPnt1, varPnt2)
        
    varPnt1 = dblPnt
    varPnt1(1) = dC / 2# - dT
    varPnt2 = dblPnt
    varPnt2(0) = 1#
    varPnt2(1) = dC / 2# - dT
    AecDtlApplication.Recipe.SetEntityProperties "hidden", blkdef.AddLine(varPnt1, varPnt2)
                
    ' start the jig
    Dim status As AecDtlPromptStatus
    status = AecDtlApplication.jig.StretchBlock(blkdef)

    ' return the status
    AecDtlApplication.Recipe.ReturnStatus = status

End Sub
Private Function CreateUBeam(ByVal dblWidth As Double, ByVal dblHeight As Double, ByVal dblThick As Double, ByVal dblCornerRad As Double, ByVal strEntityProps As String) As AcadBlock

    Dim dblPnt(0 To 2) As Double
    Dim line As AcadLine
    Dim arc As AcadArc
    Dim varP1 As Variant
    Dim varP2 As Variant
    Dim varP3 As Variant
    Dim varP4 As Variant
    Dim varP5 As Variant
    Dim varP6 As Variant
    Dim varP7 As Variant
    Dim varP8 As Variant
    Dim varP9 As Variant
    Dim varP10 As Variant
    Dim varP11 As Variant
    Dim varP12 As Variant
    
    dblPnt(0) = 0#
    dblPnt(1) = 0#
    dblPnt(2) = 0#
    
    Set CreateUBeam = ThisDrawing.Blocks.Add(dblPnt, "*U")
    
    varP1 = dblPnt
    varP2 = varP1
    varP2(1) = dblHeight
    varP3 = varP1
    varP3(0) = dblWidth
    varP4 = varP2
    varP4(0) = dblWidth
    varP5 = varP2
    varP5(0) = varP5(0) + dblThick
    varP6 = varP4
    varP6(0) = varP6(0) - dblThick
    varP7 = varP5
    varP7(1) = dblThick + dblCornerRad
    varP8 = varP6
    varP8(1) = dblThick + dblCornerRad
    varP9 = varP1
    varP9(0) = dblThick + dblCornerRad
    varP9(1) = dblThick
    varP10 = varP3
    varP10(0) = varP10(0) - (dblThick + dblCornerRad)
    varP10(1) = dblThick
    varP11 = varP1
    varP11(0) = dblThick + dblCornerRad
    varP11(1) = dblThick + dblCornerRad
    varP12 = varP3
    varP12(0) = varP12(0) - (dblThick + dblCornerRad)
    varP12(1) = dblThick + dblCornerRad
    
    Set line = CreateUBeam.AddLine(varP1, varP2)
    AecDtlApplication.Recipe.SetEntityProperties strEntityProps, line
    Set line = CreateUBeam.AddLine(varP3, varP4)
    AecDtlApplication.Recipe.SetEntityProperties strEntityProps, line
    Set line = CreateUBeam.AddLine(varP1, varP3)
    AecDtlApplication.Recipe.SetEntityProperties strEntityProps, line
    Set line = CreateUBeam.AddLine(varP2, varP5)
    AecDtlApplication.Recipe.SetEntityProperties strEntityProps, line
    Set line = CreateUBeam.AddLine(varP4, varP6)
    AecDtlApplication.Recipe.SetEntityProperties strEntityProps, line
    Set line = CreateUBeam.AddLine(varP5, varP7)
    AecDtlApplication.Recipe.SetEntityProperties strEntityProps, line
    Set line = CreateUBeam.AddLine(varP6, varP8)
    AecDtlApplication.Recipe.SetEntityProperties strEntityProps, line
    Set line = CreateUBeam.AddLine(varP9, varP10)
    AecDtlApplication.Recipe.SetEntityProperties strEntityProps, line
    Set arc = CreateUBeam.AddArc(varP11, dblCornerRad, Pi, Pi * 1.5)
    AecDtlApplication.Recipe.SetEntityProperties strEntityProps, arc
    Set arc = CreateUBeam.AddArc(varP12, dblCornerRad, Pi * 1.5, 0#)
    AecDtlApplication.Recipe.SetEntityProperties strEntityProps, arc

End Function

Attribute VB_Name = "modCalcs"
Option Explicit

Public Function Pi() As Double
    Pi = 4 * Atn(1)
End Function
Public Function DegToRad() As Double
    DegToRad = Pi / 180#
End Function
Public Function RadToDeg() As Double
    RadToDeg = 180# / Pi
End Function
Public Function CDLArcSin(ByRef dblVal As Double)
    CDLArcSin = Atn(dblVal / Sqr(-dblVal * dblVal + 1))
End Function
Public Function CDLArcCos(ByRef dblVal As Double)
    CDLArcCos = Atn(-dblVal / Sqr(-dblVal * dblVal + 1)) + 2 * Atn(1)
End Function
Public Function CDLApproxEqual(ByRef dblA As Double, ByRef dblB As Double, ByRef dblPrec As Double) As Boolean

    CDLApproxEqual = False
    
    If dblA > dblB - dblPrec / 2# And dblA < dblB + dblPrec / 2# Then
        CDLApproxEqual = True
    End If

End Function
Public Function CDLAngle(ByRef p1 As Variant, ByRef p2 As Variant) As Double

    Dim dblX As Double
    Dim dblY As Double
    Dim intXs As Integer
    Dim intYs As Integer
    
    On Error GoTo ErrorTrap

    dblX = p2(0) - p1(0)
    dblY = p2(1) - p1(1)
    
    If Abs(dblX) < 0.000000001 Then
        If dblY >= 0# Then
            CDLAngle = Pi / 2#
        Else
            CDLAngle = 1.5 * Pi
        End If
        Exit Function
    End If

    If Abs(dblY) < 0.000000001 Then
        If dblX >= 0# Then
            CDLAngle = 0#
        Else
            CDLAngle = Pi
        End If
        Exit Function
    End If
    
    intXs = Sgn(dblX)
    intYs = Sgn(dblY)
    dblX = Abs(dblX)
    dblY = Abs(dblY)
    
    CDLAngle = Atn(dblY / dblX) * RadToDeg
    
    If intXs = -1 And intYs = 1 Then
        CDLAngle = 180# - CDLAngle
    End If
    If intXs = 1 And intYs = -1 Then
        CDLAngle = 360# - CDLAngle
    End If
    If intXs = -1 And intYs = -1 Then
        CDLAngle = 180# + CDLAngle
    End If
    
    If CDLAngle > 359.99999 Then
        CDLAngle = CDLAngle - 360#
    End If
        
    CDLAngle = CDLAngle * DegToRad
    
    Exit Function
    
ErrorTrap:

    MsgBox "Error CDLAngle : " & Err.Description
    
    Err.Clear

    CDLAngle = 0#

End Function
Public Function CDLDist(ByRef p1 As Variant, ByRef p2 As Variant) As Double

    Dim dblA As Double
    Dim dblB As Double

    dblA = Abs(p2(0) - p1(0)) ^ 2
    dblB = Abs(p2(1) - p1(1)) ^ 2
    
    CDLDist = Sqr(dblA + dblB)

End Function
Public Function CDLPerp(ByRef p1 As Variant, ByRef p2 As Variant, ByRef p3 As Variant, ByRef p4 As Variant) As Boolean

    On Error GoTo ErrorTrap

    CDLPerp = False
    
    If Not CDLIntLineLine(p1, p2, p3, CDLPolar(p3, CDLAngle(p1, p2) + 90# * DegToRad, 10#), p4) Then GoTo ErrorTrap
    
    CDLPerp = True
    
    Exit Function
    
ErrorTrap:
    If Err <> 0 Then
        MsgBox "Error CDLPerp : " & Err.Description
    End If
    
    Err.Clear
    
    p4 = p3


End Function
Public Function CDLIntLineLine(ByRef p1 As Variant, ByRef p2 As Variant, ByRef p3 As Variant, ByRef p4 As Variant, ByRef p5 As Variant) As Boolean

    On Error GoTo ErrorTrap

    Dim D As Double
    Dim Dp As Double
    Dim dC As Double
    Dim tp As Double
    Dim tc As Double
    
    Dim tmpPnt(0 To 2) As Double
    
    CDLIntLineLine = False
    
    D = (p2(0) - p1(0)) * (p3(1) - p4(1)) - (p3(0) - p4(0)) * (p2(1) - p1(1))
    
    If CDLApproxEqual(D, 0#, 0.00001) Then GoTo ErrorTrap

    Dp = (p3(0) - p1(0)) * (p3(1) - p4(1)) - (p3(0) - p4(0)) * (p3(1) - p1(1))
    dC = (p2(0) - p1(0)) * (p3(1) - p1(1)) - (p3(0) - p1(0)) * (p2(1) - p1(1))

    tp = Dp / D
    tc = dC / D
    
    tmpPnt(0) = p1(0) + tp * (p2(0) - p1(0))
    tmpPnt(1) = p1(1) + tp * (p2(1) - p1(1))
    tmpPnt(2) = 0#

    p5 = tmpPnt
    
    CDLIntLineLine = True
    
    Exit Function
        
ErrorTrap:
    If Err <> 0 Then
        MsgBox "Error CDLIntLineLine : " & Err.Description
    End If
    
    Err.Clear

    p5 = p1
    
End Function
Public Function CDLPolar(ByRef p1 As Variant, ByRef dblAngle As Double, ByRef dblDist As Double) As Variant

    Dim tmpPnt(0 To 2) As Double

    On Error GoTo ErrorTrap

    tmpPnt(0) = p1(0) + Cos(dblAngle) * dblDist
    tmpPnt(1) = p1(1) + Sin(dblAngle) * dblDist
    tmpPnt(2) = 0#
    
    CDLPolar = tmpPnt
    
    Exit Function

ErrorTrap:

    MsgBox "Error CDLPolar : " & Err.Description
    
    Err.Clear
    
    CDLPolar = p1

End Function
