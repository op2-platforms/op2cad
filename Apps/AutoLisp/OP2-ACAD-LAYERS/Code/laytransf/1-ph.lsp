; file usage: phasing commands and string data for laytranf function
;
(defun c:-E (/ alpha omega) 
  (setq alpha ""
        omega "E"
  )
  (search-ph alpha omega)
)
(defun c:E- (/ alpha omega) 
  (setq alpha "E"
        omega ""
  )
  (search-ph alpha omega)
)
(defun c:E-DEMO (/ alpha omega) 
  (setq alpha "E"
        omega "D"
  )
  (search-ph alpha omega)
)
(defun c:E-NEWW (/ alpha omega) 
  (setq alpha "E"
        omega "N"
  )
  (search-ph alpha omega)
)
(defun c:E-SAVE (/ alpha omega) 
  (setq alpha "E"
        omega "S"
  )
  (search-ph alpha omega)
)
(defun c:E-MOVE (/ alpha omega) 
  (setq alpha "E"
        omega "M"
  )
  (search-ph alpha omega)
)
(defun c:E-XNOT (/ alpha omega) 
  (setq alpha "E"
        omega "X"
  )
  (search-ph alpha omega)
)
(defun c:E-TEMP (/ alpha omega) 
  (setq alpha "E"
        omega "T"
  )
  (search-ph alpha omega)
)
(defun c:E-RFSH (/ alpha omega) 
  (setq alpha "E"
        omega "R"
  )
  (search-ph alpha omega)
)
(defun c:E-ABND (/ alpha omega) 
  (setq alpha "E"
        omega "A"
  )
  (search-ph alpha omega)
)
(defun c:E-FUTW (/ alpha omega) 
  (setq alpha "E"
        omega "F"
  )
  (search-ph alpha omega)
)
(defun c:E-PROW (/ alpha omega) 
  (setq alpha "E"
        omega "P"
  )
  (search-ph alpha omega)
)



(defun c:-D (/ alpha omega) 
  (setq alpha ""
        omega "D"
  )
  (search-ph alpha omega)
)
(defun c:D- (/ alpha omega) 
  (setq alpha "D"
        omega ""
  )
  (search-ph alpha omega)
)
(defun c:D-EXST (/ alpha omega) 
  (setq alpha "D"
        omega "E"
  )
  (search-ph alpha omega)
)
(defun c:D-NEWW (/ alpha omega) 
  (setq alpha "D"
        omega "N"
  )
  (search-ph alpha omega)
)
(defun c:D-SAVE (/ alpha omega) 
  (setq alpha "D"
        omega "S"
  )
  (search-ph alpha omega)
)
(defun c:D-MOVE (/ alpha omega) 
  (setq alpha "D"
        omega "M"
  )
  (search-ph alpha omega)
)
(defun c:D-XNOT (/ alpha omega) 
  (setq alpha "D"
        omega "X"
  )
  (search-ph alpha omega)
)
(defun c:D-TEMP (/ alpha omega) 
  (setq alpha "D"
        omega "T"
  )
  (search-ph alpha omega)
)
(defun c:D-RFSH (/ alpha omega) 
  (setq alpha "D"
        omega "R"
  )
  (search-ph alpha omega)
)
(defun c:D-ABND (/ alpha omega) 
  (setq alpha "D"
        omega "A"
  )
  (search-ph alpha omega)
)
(defun c:D-FUTW (/ alpha omega) 
  (setq alpha "D"
        omega "F"
  )
  (search-ph alpha omega)
)
(defun c:D-PROW (/ alpha omega) 
  (setq alpha "D"
        omega "P"
  )
  (search-ph alpha omega)
)



(defun c:-N (/ alpha omega) 
  (setq alpha ""
        omega "N"
  )
  (search-ph alpha omega)
)
(defun c:N- (/ alpha omega) 
  (setq alpha "N"
        omega ""
  )
  (search-ph alpha omega)
)
(defun c:N-DEMO (/ alpha omega) 
  (setq alpha "N"
        omega "D"
  )
  (search-ph alpha omega)
)
(defun c:N-EXST (/ alpha omega) 
  (setq alpha "N"
        omega "E"
  )
  (search-ph alpha omega)
)
(defun c:N-SAVE (/ alpha omega) 
  (setq alpha "N"
        omega "S"
  )
  (search-ph alpha omega)
)
(defun c:N-MOVE (/ alpha omega) 
  (setq alpha "N"
        omega "M"
  )
  (search-ph alpha omega)
)
(defun c:N-XNOT (/ alpha omega) 
  (setq alpha "N"
        omega "X"
  )
  (search-ph alpha omega)
)
(defun c:N-TEMP (/ alpha omega) 
  (setq alpha "N"
        omega "T"
  )
  (search-ph alpha omega)
)
(defun c:N-RFSH (/ alpha omega) 
  (setq alpha "N"
        omega "R"
  )
  (search-ph alpha omega)
)
(defun c:N-ABND (/ alpha omega) 
  (setq alpha "N"
        omega "A"
  )
  (search-ph alpha omega)
)
(defun c:N-FUTW (/ alpha omega) 
  (setq alpha "N"
        omega "F"
  )
  (search-ph alpha omega)
)
(defun c:N-PROW (/ alpha omega) 
  (setq alpha "N"
        omega "P"
  )
  (search-ph alpha omega)
)



(defun c:-S (/ alpha omega) 
  (setq alpha ""
        omega "S"
  )
  (search-ph alpha omega)
)
(defun c:S- (/ alpha omega) 
  (setq alpha "S"
        omega ""
  )
  (search-ph alpha omega)
)
(defun c:S-DEMO (/ alpha omega) 
  (setq alpha "S"
        omega "D"
  )
  (search-ph alpha omega)
)
(defun c:S-NEWW (/ alpha omega) 
  (setq alpha "S"
        omega "N"
  )
  (search-ph alpha omega)
)
(defun c:S-SAVE (/ alpha omega) 
  (setq alpha "S"
        omega "E"
  )
  (search-ph alpha omega)
)
(defun c:S-MOVE (/ alpha omega) 
  (setq alpha "S"
        omega "M"
  )
  (search-ph alpha omega)
)
(defun c:S-XNOT (/ alpha omega) 
  (setq alpha "S"
        omega "X"
  )
  (search-ph alpha omega)
)
(defun c:S-TEMP (/ alpha omega) 
  (setq alpha "S"
        omega "T"
  )
  (search-ph alpha omega)
)
(defun c:S-RFSH (/ alpha omega) 
  (setq alpha "S"
        omega "R"
  )
  (search-ph alpha omega)
)
(defun c:S-ABND (/ alpha omega) 
  (setq alpha "S"
        omega "A"
  )
  (search-ph alpha omega)
)
(defun c:S-FUTW (/ alpha omega) 
  (setq alpha "S"
        omega "F"
  )
  (search-ph alpha omega)
)
(defun c:S-PROW (/ alpha omega) 
  (setq alpha "S"
        omega "P"
  )
  (search-ph alpha omega)
)



(defun c:-M (/ alpha omega) 
  (setq alpha ""
        omega "M"
  )
  (search-ph alpha omega)
)
(defun c:M- (/ alpha omega) 
  (setq alpha "M"
        omega ""
  )
  (search-ph alpha omega)
)
(defun c:M-DEMO (/ alpha omega) 
  (setq alpha "M"
        omega "D"
  )
  (search-ph alpha omega)
)
(defun c:M-NEWW (/ alpha omega) 
  (setq alpha "M"
        omega "N"
  )
  (search-ph alpha omega)
)
(defun c:M-SAVE (/ alpha omega) 
  (setq alpha "M"
        omega "S"
  )
  (search-ph alpha omega)
)
(defun c:M-EXST (/ alpha omega) 
  (setq alpha "M"
        omega "E"
  )
  (search-ph alpha omega)
)
(defun c:M-XNOT (/ alpha omega) 
  (setq alpha "M"
        omega "X"
  )
  (search-ph alpha omega)
)
(defun c:M-TEMP (/ alpha omega) 
  (setq alpha "M"
        omega "T"
  )
  (search-ph alpha omega)
)
(defun c:M-RFSH (/ alpha omega) 
  (setq alpha "M"
        omega "R"
  )
  (search-ph alpha omega)
)
(defun c:M-ABND (/ alpha omega) 
  (setq alpha "M"
        omega "A"
  )
  (search-ph alpha omega)
)
(defun c:M-FUTW (/ alpha omega) 
  (setq alpha "M"
        omega "F"
  )
  (search-ph alpha omega)
)
(defun c:M-PROW (/ alpha omega) 
  (setq alpha "M"
        omega "P"
  )
  (search-ph alpha omega)
)


(defun c:-R (/ alpha omega) 
  (setq alpha ""
        omega "R"
  )
  (search-ph alpha omega)
)
(defun c:R- (/ alpha omega) 
  (setq alpha "R"
        omega ""
  )
  (search-ph alpha omega)
)
(defun c:R-DEMO (/ alpha omega) 
  (setq alpha "R"
        omega "D"
  )
  (search-ph alpha omega)
)
(defun c:R-NEWW (/ alpha omega) 
  (setq alpha "R"
        omega "N"
  )
  (search-ph alpha omega)
)
(defun c:R-SAVE (/ alpha omega) 
  (setq alpha "R"
        omega "S"
  )
  (search-ph alpha omega)
)
(defun c:R-MOVE (/ alpha omega) 
  (setq alpha "R"
        omega "M"
  )
  (search-ph alpha omega)
)
(defun c:R-XNOT (/ alpha omega) 
  (setq alpha "R"
        omega "X"
  )
  (search-ph alpha omega)
)
(defun c:R-TEMP (/ alpha omega) 
  (setq alpha "R"
        omega "T"
  )
  (search-ph alpha omega)
)
(defun c:R-EXST (/ alpha omega) 
  (setq alpha "R"
        omega "E"
  )
  (search-ph alpha omega)
)
(defun c:R-ABND (/ alpha omega) 
  (setq alpha "R"
        omega "A"
  )
  (search-ph alpha omega)
)
(defun c:R-FUTW (/ alpha omega) 
  (setq alpha "R"
        omega "F"
  )
  (search-ph alpha omega)
)
(defun c:R-PROW (/ alpha omega) 
  (setq alpha "R"
        omega "P"
  )
  (search-ph alpha omega)
)
