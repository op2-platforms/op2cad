; layer addition commands for layer states and views management

; phase
(defun c:la-1 () 
  (command "-layer" "on" "*-1" "t" "*-1" "")
  (princ)
)
(defun c:la-2 () 
  (command "-layer" "on" "*-2" "t" "*-2" "")
  (princ)
)
(defun c:la-3 () 
  (command "-layer" "on" "*-3" "t" "*-3" "")
  (princ)
)
(defun c:la-4 () 
  (command "-layer" "on" "*-4" "t" "*-4" "")
  (princ)
)
(defun c:la-5 () 
  (command "-layer" "on" "*-5" "t" "*-5" "")
  (princ)
)
(defun c:la-6 () 
  (command "-layer" "on" "*-6" "t" "*-6" "")
  (princ)
)
(defun c:la-7 () 
  (command "-layer" "on" "*-7" "t" "*-7" "")
  (princ)
)
(defun c:la-8 () 
  (command "-layer" "on" "*-8" "t" "*-8" "")
  (princ)
)
(defun c:la-9 () 
  (command "-layer" "on" "*-9" "t" "*-9" "")
  (princ)
)

; status
(defun c:la-neww () 
  (command "-layer" "on" "*-N" "t" "*-N" "")
  (princ)
)
(defun c:la-exst () 
  (command "-layer" "on" "*-E" "t" "*-E" "")
  (princ)
)
(defun c:la-demo () 
  (command "-layer" "on" "*-D" "t" "*-D" "")
  (princ)
)
(defun c:la-move () 
  (command "-layer" "on" "*-M" "t" "*-M" "")
  (princ)
)
(defun c:la-abnd () 
  (command "-layer" "on" "*-A" "t" "*-A" "")
  (princ)
)
(defun c:la-rfsh () 
  (command "-layer" "on" "*-R" "t" "*-R" "")
  (princ)
)
(defun c:la-temp () 
  (command "-layer" "on" "*-T" "t" "*-T" "")
  (princ)
)
(defun c:la-prow () 
  (command "-layer" "on" "*-P" "t" "*-P" "")
  (princ)
)
(defun c:la-futw () 
  (command "-layer" "on" "*-F" "t" "*-F" "")
  (princ)
)
(defun c:la-save () 
  (command "-layer" "on" "*-S" "t" "*-S" "")
  (princ)
)
