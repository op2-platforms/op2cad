; layer color greying commands for layer states and views management

; phase
(defun c:lg-1 () 
  (command "-layer" "c" "009" "*-1")
  (princ)
)
(defun c:lg-2 () 
  (command "-layer" "c" "009" "*-2")
  (princ)
)
(defun c:lg-3 () 
  (command "-layer" "c" "009" "*-3")
  (princ)
)
(defun c:lg-4 () 
  (command "-layer" "c" "009" "*-4")
  (princ)
)
(defun c:lg-5 () 
  (command "-layer" "c" "009" "*-5")
  (princ)
)
(defun c:lg-6 () 
  (command "-layer" "c" "009" "*-6")
  (princ)
)
(defun c:lg-7 () 
  (command "-layer" "c" "009" "*-7")
  (princ)
)
(defun c:lg-8 () 
  (command "-layer" "c" "009" "*-8")
  (princ)
)
(defun c:lg-9 () 
  (command "-layer" "c" "009" "*-9")
  (princ)
)

; status
(defun c:lg-neww () 
  (command "-layer" "c" "009" "*-N")
  (princ)
)
(defun c:lg-exst () 
  (command "-layer" "c" "009" "*-E")
  (princ)
)
(defun c:lg-demo () 
  (command "-layer" "c" "009" "*-D")
  (princ)
)
(defun c:lg-move () 
  (command "-layer" "c" "009" "*-M")
  (princ)
)
(defun c:lg-abnd () 
  (command "-layer" "c" "009" "*-A")
  (princ)
)
(defun c:lg-rfsh () 
  (command "-layer" "c" "009" "*-R")
  (princ)
)
(defun c:lg-temp () 
  (command "-layer" "c" "009" "*-T")
  (princ)
)
(defun c:lg-prow () 
  (command "-layer" "c" "009" "*-P")
  (princ)
)
(defun c:lg-futw () 
  (command "-layer" "c" "009" "*-F")
  (princ)
)
(defun c:lg-save () 
  (command "-layer" "c" "009" "*-S")
  (princ)
)
