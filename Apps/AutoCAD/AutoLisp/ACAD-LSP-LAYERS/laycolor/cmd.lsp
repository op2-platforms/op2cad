; layer color greying commands for layer states and views management

; phase
(defun c:lc-1 (/ _lay) 
  (setq _lay "*-1")
  (laycolor _lay)
)
(defun c:lc-2 (/ _lay) 
  (setq _lay "*-2")
  (laycolor _lay)
)
(defun c:lc-3 (/ _lay) 
  (setq _lay "*-3")
  (laycolor _lay)
)
(defun c:lc-4 (/ _lay) 
  (setq _lay "*-4")
  (laycolor _lay)
)
(defun c:lc-5 (/ _lay) 
  (setq _lay "*-5")
  (laycolor _lay)
)
(defun c:lc-6 (/ _lay) 
  (setq _lay "*-6")
  (laycolor _lay)
)
(defun c:lc-7 (/ _lay) 
  (setq _lay "*-7")
  (laycolor _lay)
)
(defun c:lc-8 (/ _lay) 
  (setq _lay "*-8")
  (laycolor _lay)
)
(defun c:lc-9 (/ _lay) 
  (setq _lay "*-9")
  (laycolor _lay)
)

; status
(defun c:lc-neww (/ _lay) 
  (setq _lay "*-N")
  (laycolor _lay)
)
(defun c:lc-exst (/ _lay) 
  (setq _lay "*-E")
  (laycolor _lay)
)
(defun c:lc-demo (/ _lay) 
  (setq _lay "*-D")
  (laycolor _lay)
)
(defun c:lc-move (/ _lay) 
  (setq _lay "*-M")
  (laycolor _lay)
)
(defun c:lc-abnd (/ _lay) 
  (setq _lay "*-A")
  (laycolor _lay)
)
(defun c:lc-rfsh (/ _lay) 
  (setq _lay "*-R")
  (laycolor _lay)
)
(defun c:lc-temp (/ _lay) 
  (setq _lay "*-T")
  (laycolor _lay)
)
(defun c:lc-prow (/ _lay) 
  (setq _lay "*-P")
  (laycolor _lay)
)
(defun c:lc-futw (/ _lay) 
  (setq _lay "*-F")
  (laycolor _lay)
)
(defun c:lc-save (/ _lay) 
  (setq _lay "*-S")
  (laycolor _lay)
)

(defun laycolor (_lay /) 
  (command "-layer" "c" _lay "f" _lay "")
  (princ)
)
