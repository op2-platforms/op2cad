; file usage: phasing commands and string data for laytranf function
;
(defun c:-E (/ alpha omega) 
    (setq alpha ""
          omega "E"
    )
    (laytransf alpha omega)
)
(defun c:E- (/ alpha omega) 
    (setq alpha "E"
          omega ""
    )
    (laytransf alpha omega)
)
(defun c:E-DEMO (/ alpha omega) 
    (setq alpha "E"
          omega "D"
    )
    (laytransf alpha omega)
)
(defun c:E-NEWW (/ alpha omega) 
    (setq alpha "E"
          omega "N"
    )
    (laytransf alpha omega)
)
(defun c:E-SAVE (/ alpha omega) 
    (setq alpha "E"
          omega "S"
    )
    (laytransf alpha omega)
)
(defun c:E-MOVE (/ alpha omega) 
    (setq alpha "E"
          omega "M"
    )
    (laytransf alpha omega)
)
(defun c:E-XNOT (/ alpha omega) 
    (setq alpha "E"
          omega "X"
    )
    (laytransf alpha omega)
)
(defun c:E-TEMP (/ alpha omega) 
    (setq alpha "E"
          omega "T"
    )
    (laytransf alpha omega)
)
(defun c:E-RFSH (/ alpha omega) 
    (setq alpha "E"
          omega "R"
    )
    (laytransf alpha omega)
)
(defun c:E-ABND (/ alpha omega) 
    (setq alpha "E"
          omega "A"
    )
    (laytransf alpha omega)
)
(defun c:E-FUTW (/ alpha omega) 
    (setq alpha "E"
          omega "F"
    )
    (laytransf alpha omega)
)
(defun c:E-PROW (/ alpha omega) 
    (setq alpha "E"
          omega "P"
    )
    (laytransf alpha omega)
)



(defun c:-D (/ alpha omega) 
    (setq alpha ""
          omega "D"
    )
    (laytransf alpha omega)
)
(defun c:D- (/ alpha omega) 
    (setq alpha "D"
          omega ""
    )
    (laytransf alpha omega)
)
(defun c:D-EXST (/ alpha omega) 
    (setq alpha "D"
          omega "E"
    )
    (laytransf alpha omega)
)
(defun c:D-NEWW (/ alpha omega) 
    (setq alpha "D"
          omega "N"
    )
    (laytransf alpha omega)
)
(defun c:D-SAVE (/ alpha omega) 
    (setq alpha "D"
          omega "S"
    )
    (laytransf alpha omega)
)
(defun c:D-MOVE (/ alpha omega) 
    (setq alpha "D"
          omega "M"
    )
    (laytransf alpha omega)
)
(defun c:D-XNOT (/ alpha omega) 
    (setq alpha "D"
          omega "X"
    )
    (laytransf alpha omega)
)
(defun c:D-TEMP (/ alpha omega) 
    (setq alpha "D"
          omega "T"
    )
    (laytransf alpha omega)
)
(defun c:D-RFSH (/ alpha omega) 
    (setq alpha "D"
          omega "R"
    )
    (laytransf alpha omega)
)
(defun c:D-ABND (/ alpha omega) 
    (setq alpha "D"
          omega "A"
    )
    (laytransf alpha omega)
)
(defun c:D-FUTW (/ alpha omega) 
    (setq alpha "D"
          omega "F"
    )
    (laytransf alpha omega)
)
(defun c:D-PROW (/ alpha omega) 
    (setq alpha "D"
          omega "P"
    )
    (laytransf alpha omega)
)



(defun c:-N (/ alpha omega) 
    (setq alpha ""
          omega "N"
    )
    (laytransf alpha omega)
)
(defun c:N- (/ alpha omega) 
    (setq alpha "N"
          omega ""
    )
    (laytransf alpha omega)
)
(defun c:N-DEMO (/ alpha omega) 
    (setq alpha "N"
          omega "D"
    )
    (laytransf alpha omega)
)
(defun c:N-EXST (/ alpha omega) 
    (setq alpha "N"
          omega "E"
    )
    (laytransf alpha omega)
)
(defun c:N-SAVE (/ alpha omega) 
    (setq alpha "N"
          omega "S"
    )
    (laytransf alpha omega)
)
(defun c:N-MOVE (/ alpha omega) 
    (setq alpha "N"
          omega "M"
    )
    (laytransf alpha omega)
)
(defun c:N-XNOT (/ alpha omega) 
    (setq alpha "N"
          omega "X"
    )
    (laytransf alpha omega)
)
(defun c:N-TEMP (/ alpha omega) 
    (setq alpha "N"
          omega "T"
    )
    (laytransf alpha omega)
)
(defun c:N-RFSH (/ alpha omega) 
    (setq alpha "N"
          omega "R"
    )
    (laytransf alpha omega)
)
(defun c:N-ABND (/ alpha omega) 
    (setq alpha "N"
          omega "A"
    )
    (laytransf alpha omega)
)
(defun c:N-FUTW (/ alpha omega) 
    (setq alpha "N"
          omega "F"
    )
    (laytransf alpha omega)
)
(defun c:N-PROW (/ alpha omega) 
    (setq alpha "N"
          omega "P"
    )
    (laytransf alpha omega)
)



(defun c:-S (/ alpha omega) 
    (setq alpha ""
          omega "S"
    )
    (laytransf alpha omega)
)
(defun c:S- (/ alpha omega) 
    (setq alpha "S"
          omega ""
    )
    (laytransf alpha omega)
)
(defun c:S-DEMO (/ alpha omega) 
    (setq alpha "S"
          omega "D"
    )
    (laytransf alpha omega)
)
(defun c:S-NEWW (/ alpha omega) 
    (setq alpha "S"
          omega "N"
    )
    (laytransf alpha omega)
)
(defun c:S-SAVE (/ alpha omega) 
    (setq alpha "S"
          omega "E"
    )
    (laytransf alpha omega)
)
(defun c:S-MOVE (/ alpha omega) 
    (setq alpha "S"
          omega "M"
    )
    (laytransf alpha omega)
)
(defun c:S-XNOT (/ alpha omega) 
    (setq alpha "S"
          omega "X"
    )
    (laytransf alpha omega)
)
(defun c:S-TEMP (/ alpha omega) 
    (setq alpha "S"
          omega "T"
    )
    (laytransf alpha omega)
)
(defun c:S-RFSH (/ alpha omega) 
    (setq alpha "S"
          omega "R"
    )
    (laytransf alpha omega)
)
(defun c:S-ABND (/ alpha omega) 
    (setq alpha "S"
          omega "A"
    )
    (laytransf alpha omega)
)
(defun c:S-FUTW (/ alpha omega) 
    (setq alpha "S"
          omega "F"
    )
    (laytransf alpha omega)
)
(defun c:S-PROW (/ alpha omega) 
    (setq alpha "S"
          omega "P"
    )
    (laytransf alpha omega)
)



(defun c:-M (/ alpha omega) 
    (setq alpha ""
          omega "M"
    )
    (laytransf alpha omega)
)
(defun c:M- (/ alpha omega) 
    (setq alpha "M"
          omega ""
    )
    (laytransf alpha omega)
)
(defun c:M-DEMO (/ alpha omega) 
    (setq alpha "M"
          omega "D"
    )
    (laytransf alpha omega)
)
(defun c:M-NEWW (/ alpha omega) 
    (setq alpha "M"
          omega "N"
    )
    (laytransf alpha omega)
)
(defun c:M-SAVE (/ alpha omega) 
    (setq alpha "M"
          omega "S"
    )
    (laytransf alpha omega)
)
(defun c:M-EXST (/ alpha omega) 
    (setq alpha "M"
          omega "E"
    )
    (laytransf alpha omega)
)
(defun c:M-XNOT (/ alpha omega) 
    (setq alpha "M"
          omega "X"
    )
    (laytransf alpha omega)
)
(defun c:M-TEMP (/ alpha omega) 
    (setq alpha "M"
          omega "T"
    )
    (laytransf alpha omega)
)
(defun c:M-RFSH (/ alpha omega) 
    (setq alpha "M"
          omega "R"
    )
    (laytransf alpha omega)
)
(defun c:M-ABND (/ alpha omega) 
    (setq alpha "M"
          omega "A"
    )
    (laytransf alpha omega)
)
(defun c:M-FUTW (/ alpha omega) 
    (setq alpha "M"
          omega "F"
    )
    (laytransf alpha omega)
)
(defun c:M-PROW (/ alpha omega) 
    (setq alpha "M"
          omega "P"
    )
    (laytransf alpha omega)
)


(defun c:-R (/ alpha omega) 
    (setq alpha ""
          omega "R"
    )
    (laytransf alpha omega)
)
(defun c:R- (/ alpha omega) 
    (setq alpha "R"
          omega ""
    )
    (laytransf alpha omega)
)
(defun c:R-DEMO (/ alpha omega) 
    (setq alpha "R"
          omega "D"
    )
    (laytransf alpha omega)
)
(defun c:R-NEWW (/ alpha omega) 
    (setq alpha "R"
          omega "N"
    )
    (laytransf alpha omega)
)
(defun c:R-SAVE (/ alpha omega) 
    (setq alpha "R"
          omega "S"
    )
    (laytransf alpha omega)
)
(defun c:R-MOVE (/ alpha omega) 
    (setq alpha "R"
          omega "M"
    )
    (laytransf alpha omega)
)
(defun c:R-XNOT (/ alpha omega) 
    (setq alpha "R"
          omega "X"
    )
    (laytransf alpha omega)
)
(defun c:R-TEMP (/ alpha omega) 
    (setq alpha "R"
          omega "T"
    )
    (laytransf alpha omega)
)
(defun c:R-EXST (/ alpha omega) 
    (setq alpha "R"
          omega "E"
    )
    (laytransf alpha omega)
)
(defun c:R-ABND (/ alpha omega) 
    (setq alpha "R"
          omega "A"
    )
    (laytransf alpha omega)
)
(defun c:R-FUTW (/ alpha omega) 
    (setq alpha "R"
          omega "F"
    )
    (laytransf alpha omega)
)
(defun c:R-PROW (/ alpha omega) 
    (setq alpha "R"
          omega "P"
    )
    (laytransf alpha omega)
)
