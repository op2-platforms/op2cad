; file usage: minor 1 commands and string data for laytranf function
;
;#region ACCESS
(defun c:m1-accs-clng (/ alpha omega) 
    (setq alpha "ACCS"
          omega "CLNG"
    )
    (laytransf alpha omega)
)
(defun c:m1-accs-code (/ alpha omega) 
    (setq alpha "ACCS"
          omega "CODE"
    )
    (laytransf alpha omega)
)
(defun c:m1-accs-domw (/ alpha omega) 
    (setq alpha "ACCS"
          omega "DOMW"
    )
    (laytransf alpha omega)
)
(defun c:m1-accs-elec (/ alpha omega) 
    (setq alpha "ACCS"
          omega "ELEC"
    )
    (laytransf alpha omega)
)
(defun c:m1-accs-evac (/ alpha omega) 
    (setq alpha "ACCS"
          omega "EVAC"
    )
    (laytransf alpha omega)
)
(defun c:m1-accs-fire (/ alpha omega) 
    (setq alpha "ACCS"
          omega "FIRE"
    )
    (laytransf alpha omega)
)
(defun c:m1-accs-flor (/ alpha omega) 
    (setq alpha "ACCS"
          omega "FLOR"
    )
    (laytransf alpha omega)
)
(defun c:m1-accs-fndn (/ alpha omega) 
    (setq alpha "ACCS"
          omega "FNDN"
    )
    (laytransf alpha omega)
)
(defun c:m1-accs-furn (/ alpha omega) 
    (setq alpha "ACCS"
          omega "FURN"
    )
    (laytransf alpha omega)
)
(defun c:m1-accs-HVAC (/ alpha omega) 
    (setq alpha "ACCS"
          omega "HVAC"
    )
    (laytransf alpha omega)
)
(defun c:m1-accs-code (/ alpha omega) 
    (setq alpha "ACCS"
          omega "ROOF"
    )
    (laytransf alpha omega)
)
(defun c:m1-accs-site (/ alpha omega) 
    (setq alpha "ACCS"
          omega "SITE"
    )
    (laytransf alpha omega)
)
(defun c:m1-accs-sswr (/ alpha omega) 
    (setq alpha "ACCS"
          omega "SSWR"
    )
    (laytransf alpha omega)
)
(defun c:m1-accs-strc (/ alpha omega) 
    (setq alpha "ACCS"
          omega "STRC"
    )
    (laytransf alpha omega)
)
(defun c:m1-accs-0001 (/ alpha omega) 
    (setq alpha "ACCS"
          omega "0001"
    )
    (laytransf alpha omega)
)
(defun c:m1-accs-0002 (/ alpha omega) 
    (setq alpha "ACCS"
          omega "0002"
    )
    (laytransf alpha omega)
)
(defun c:m1-accs-0003 (/ alpha omega) 
    (setq alpha "ACCS"
          omega "0003"
    )
    (laytransf alpha omega)
)
;#endregion

;#region CEILING
(defun c:m1-clng-accs (/ alpha omega) 
    (setq alpha "CLNG"
          omega "ACCS"
    )
    (laytransf alpha omega)
)
(defun c:m1-clng-code (/ alpha omega) 
    (setq alpha "CLNG"
          omega "CODE"
    )
    (laytransf alpha omega)
)
(defun c:m1-clng-domw (/ alpha omega) 
    (setq alpha "CLNG"
          omega "DOMW"
    )
    (laytransf alpha omega)
)
(defun c:m1-clng-elec (/ alpha omega) 
    (setq alpha "CLNG"
          omega "ELEC"
    )
    (laytransf alpha omega)
)
(defun c:m1-clng-evac (/ alpha omega) 
    (setq alpha "CLNG"
          omega "EVAC"
    )
    (laytransf alpha omega)
)
(defun c:m1-clng-fire (/ alpha omega) 
    (setq alpha "CLNG"
          omega "FIRE"
    )
    (laytransf alpha omega)
)
(defun c:m1-clng-flor (/ alpha omega) 
    (setq alpha "CLNG"
          omega "FLOR"
    )
    (laytransf alpha omega)
)
(defun c:m1-clng-fndn (/ alpha omega) 
    (setq alpha "CLNG"
          omega "FNDN"
    )
    (laytransf alpha omega)
)
(defun c:m1-clng-furn (/ alpha omega) 
    (setq alpha "CLNG"
          omega "FURN"
    )
    (laytransf alpha omega)
)
(defun c:m1-clng-HVAC (/ alpha omega) 
    (setq alpha "CLNG"
          omega "HVAC"
    )
    (laytransf alpha omega)
)
(defun c:m1-clng-code (/ alpha omega) 
    (setq alpha "CLNG"
          omega "ROOF"
    )
    (laytransf alpha omega)
)
(defun c:m1-clng-site (/ alpha omega) 
    (setq alpha "CLNG"
          omega "SITE"
    )
    (laytransf alpha omega)
)
(defun c:m1-clng-sswr (/ alpha omega) 
    (setq alpha "CLNG"
          omega "SSWR"
    )
    (laytransf alpha omega)
)
(defun c:m1-clng-strc (/ alpha omega) 
    (setq alpha "CLNG"
          omega "STRC"
    )
    (laytransf alpha omega)
)
(defun c:m1-clng-0001 (/ alpha omega) 
    (setq alpha "CLNG"
          omega "0001"
    )
    (laytransf alpha omega)
)
(defun c:m1-clng-0002 (/ alpha omega) 
    (setq alpha "CLNG"
          omega "0002"
    )
    (laytransf alpha omega)
)
(defun c:m1-clng-0003 (/ alpha omega) 
    (setq alpha "CLNG"
          omega "0003"
    )
    (laytransf alpha omega)
)
;#endregion

;#region FINE
(defun c:m1-fine-xfin (/ alpha omega) 
    (setq alpha "FINE"
          omega "XFIN"
    )
    (laytransf alpha omega)
)
(defun c:m1-fine-thin (/ alpha omega) 
    (setq alpha "FINE"
          omega "THIN"
    )
    (laytransf alpha omega)
)
(defun c:m1-fine-medm (/ alpha omega) 
    (setq alpha "FINE"
          omega "MEDM"
    )
    (laytransf alpha omega)
)
(defun c:m1-fine-wide (/ alpha omega) 
    (setq alpha "FINE"
          omega "WIDE"
    )
    (laytransf alpha omega)
)
(defun c:m1-fine-x~~~ (/ alpha omega) 
    (setq alpha "FINE"
          omega "X~~~"
    )
    (laytransf alpha omega)
)
(defun c:m1-fine-x~~~ (/ alpha omega) 
    (setq alpha "FINE"
          omega "XX~~"
    )
    (laytransf alpha omega)
)
(defun c:m1-fine-x~~~ (/ alpha omega) 
    (setq alpha "FINE"
          omega "XXX~"
    )
    (laytransf alpha omega)
)
(defun c:m1-fine-x~~~ (/ alpha omega) 
    (setq alpha "FINE"
          omega "XXXX"
    )
    (laytransf alpha omega)
)
(defun c:m1-fine-patt (/ alpha omega) 
    (setq alpha "FINE"
          omega "PATT"
    )
    (laytransf alpha omega)
)
(defun c:m1-fine-scrn (/ alpha omega) 
    (setq alpha "FINE"
          omega "SCRN"
    )
    (laytransf alpha omega)
)
;#endregion

;#region thin
(defun c:m1-thin-xfin (/ alpha omega) 
    (setq alpha "THIN"
          omega "XFIN"
    )
    (laytransf alpha omega)
)
(defun c:m1-thin-fine (/ alpha omega) 
    (setq alpha "THIN"
          omega "FINE"
    )
    (laytransf alpha omega)
)
(defun c:m1-thin-medm (/ alpha omega) 
    (setq alpha "THIN"
          omega "MEDM"
    )
    (laytransf alpha omega)
)
(defun c:m1-thin-wide (/ alpha omega) 
    (setq alpha "THIN"
          omega "WIDE"
    )
    (laytransf alpha omega)
)
(defun c:m1-thin-x~~~ (/ alpha omega) 
    (setq alpha "THIN"
          omega "X~~~"
    )
    (laytransf alpha omega)
)
(defun c:m1-thin-x~~~ (/ alpha omega) 
    (setq alpha "THIN"
          omega "XX~~"
    )
    (laytransf alpha omega)
)
(defun c:m1-thin-x~~~ (/ alpha omega) 
    (setq alpha "THIN"
          omega "XXX~"
    )
    (laytransf alpha omega)
)
(defun c:m1-thin-x~~~ (/ alpha omega) 
    (setq alpha "THIN"
          omega "xxxx"
    )
    (laytransf alpha omega)
)
(defun c:m1-thin-patt (/ alpha omega) 
    (setq alpha "THIN"
          omega "PATT"
    )
    (laytransf alpha omega)
)
(defun c:m1-thin-scrn (/ alpha omega) 
    (setq alpha "THIN"
          omega "SCRN"
    )
    (laytransf alpha omega)
)
;#endregion

;#region medm
(defun c:m1-medm-xfin (/ alpha omega) 
    (setq alpha "MEDM"
          omega "XFIN"
    )
    (laytransf alpha omega)
)
(defun c:m1-medm-fine (/ alpha omega) 
    (setq alpha "MEDM"
          omega "FINE"
    )
    (laytransf alpha omega)
)
(defun c:m1-medm-thin (/ alpha omega) 
    (setq alpha "MEDM"
          omega "THIN"
    )
    (laytransf alpha omega)
)
(defun c:m1-medm-wide (/ alpha omega) 
    (setq alpha "MEDM"
          omega "WIDE"
    )
    (laytransf alpha omega)
)
(defun c:m1-medm-x~~~ (/ alpha omega) 
    (setq alpha "MEDM"
          omega "X~~~"
    )
    (laytransf alpha omega)
)
(defun c:m1-medm-x~~~ (/ alpha omega) 
    (setq alpha "MEDM"
          omega "XX~~"
    )
    (laytransf alpha omega)
)
(defun c:m1-medm-x~~~ (/ alpha omega) 
    (setq alpha "MEDM"
          omega "XXX~"
    )
    (laytransf alpha omega)
)
(defun c:m1-medm-x~~~ (/ alpha omega) 
    (setq alpha "MEDM"
          omega "xxxx"
    )
    (laytransf alpha omega)
)
;#endregion

;#region wide
(defun c:m1-wide-xfin (/ alpha omega) 
    (setq alpha "WIDE"
          omega "XFIN"
    )
    (laytransf alpha omega)
)
(defun c:m1-wide-fine (/ alpha omega) 
    (setq alpha "WIDE"
          omega "FINE"
    )
    (laytransf alpha omega)
)
(defun c:m1-wide-thin (/ alpha omega) 
    (setq alpha "WIDE"
          omega "THIN"
    )
    (laytransf alpha omega)
)
(defun c:m1-wide-medm (/ alpha omega) 
    (setq alpha "WIDE"
          omega "MEDM"
    )
    (laytransf alpha omega)
)
(defun c:m1-wide-x~~~ (/ alpha omega) 
    (setq alpha "WIDE"
          omega "X~~~"
    )
    (laytransf alpha omega)
)
(defun c:m1-wide-x~~~ (/ alpha omega) 
    (setq alpha "WIDE"
          omega "XX~~"
    )
    (laytransf alpha omega)
)
(defun c:m1-wide-x~~~ (/ alpha omega) 
    (setq alpha "WIDE"
          omega "XXX~"
    )
    (laytransf alpha omega)
)
(defun c:m1-wide-x~~~ (/ alpha omega) 
    (setq alpha "WIDE"
          omega "xxxx"
    )
    (laytransf alpha omega)
)
;#endregion
