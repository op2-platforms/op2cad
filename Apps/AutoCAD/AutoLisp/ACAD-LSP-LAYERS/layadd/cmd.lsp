; layer addition commands for layer states and views management

; phase
(defun c:la-1 (/ _lay) 
  (setq _lay "*-1")
  (layadd _lay)
)
(defun c:la-2 (/ _lay) 
  (setq _lay "*-2")
  (layadd _lay)
)
(defun c:la-3 (/ _lay) 
  (setq _lay "*-3")
  (layadd _lay)
)
(defun c:la-4 (/ _lay) 
  (setq _lay "*-4")
  (layadd _lay)
)
(defun c:la-5 (/ _lay) 
  (setq _lay "*-5")
  (layadd _lay)
)
(defun c:la-6 (/ _lay) 
  (setq _lay "*-6")
  (layadd _lay)
)
(defun c:la-7 (/ _lay) 
  (setq _lay "*-7")
  (layadd _lay)
)
(defun c:la-8 (/ _lay) 
  (setq _lay "*-8")
  (layadd _lay)
)
(defun c:la-9 (/ _lay) 
  (setq _lay "*-9")
  (layadd _lay)
)

; status
(defun c:la-neww (/ _lay) 
  (setq _lay "*-N")
  (layadd _lay)
)
(defun c:la-exst (/ _lay) 
  (setq _lay "*-E")
  (layadd _lay)
)
(defun c:la-demo (/ _lay) 
  (setq _lay "*-D")
  (layadd _lay)
)
(defun c:la-move (/ _lay) 
  (setq _lay "*-M")
  (layadd _lay)
)
(defun c:la-abnd (/ _lay) 
  (setq _lay "*-A")
  (layadd _lay)
)
(defun c:la-rfsh (/ _lay) 
  (setq _lay "*-R")
  (layadd _lay)
)
(defun c:la-temp (/ _lay) 
  (setq _lay "*-T")
  (layadd _lay)
)
(defun c:la-prow (/ _lay) 
  (setq _lay "*-P")
  (layadd _lay)
)
(defun c:la-futw (/ _lay) 
  (setq _lay "*-F")
  (layadd _lay)
)
(defun c:la-save (/ _lay) 
  (setq _lay "*-S")
  (layadd _lay)
)
