(defun c:1-1 (/ impstr impsc metsc) 
  (setq impstr "1'-0\" = 1'-0\""
        impsc  "1:1"
        metsc  "1:1"
  )
  (navscale impstr impsc metsc)
)
(defun c:1-2 (/ impstr impsc metsc) 
  (setq impstr "6\" = 1'-0\""
        impsc  "1:2"
        metsc  "1:2"
  )
  (navscale impstr impsc metsc)
)
(defun c:1-5 (/ impstr impsc metsc) 
  (setq impstr "3\" = 1'-0\""
        impsc  "1:4"
        metsc  "1:5"
  )
  (navscale impstr impsc metsc)
)
(defun c:1-10 (/ impstr impsc metsc) 
  (setq impstr "1 1/2\" = 1'-0\""
        impsc  "1:8"
        metsc  "1:10"
  )
  (navscale impstr impsc metsc)
)
(defun c:1-20 (/ impstr impsc metsc) 
  (setq impstr "3/4\" = 1'-0\""
        impsc  "1:16"
        metsc  "1:20"
  )
  (navscale impstr impsc metsc)
)
(defun c:1-25 (/ impstr impsc metsc) 
  (setq impstr "1/2\" = 1'-0\""
        impsc  "1:24"
        metsc  "1:25"
  )
  (navscale impstr impsc metsc)
)
(defun c:1-40 (/ impstr impsc metsc) 
  (setq impstr "3/8\" = 1'-0\""
        impsc  "1:32"
        metsc  "1:40"
  )
  (navscale impstr impsc metsc)
)
(defun c:1-50 (/ impstr impsc metsc) 
  (setq impstr "1/4\" = 1'-0\""
        impsc  "1:48"
        metsc  "1:50"
  )
  (navscale impstr impsc metsc)
)
(defun c:1-75 (/ impstr impsc metsc) 
  (setq impstr "3/16\" = 1'-0\""
        impsc  "1:64"
        metsc  "1:75"
  )
  (navscale impstr impsc metsc)
)
(defun c:1-100 (/ impstr impsc metsc) 
  (setq impstr "1/8\" = 1'-0\""
        impsc  "1:96"
        metsc  "1:100"
  )
  (navscale impstr impsc metsc)
)
(defun c:1-125 (/ impstr impsc metsc) 
  (setq impstr "1/8\" = 1'-0\""
        impsc  "1:128"
        metsc  "1:125"
  )
  (navscale impstr impsc metsc)
)
(defun c:1-200 (/ impstr impsc metsc) 
  (setq impstr "1/16\" = 1'-0\""
        impsc  "1:192"
        metsc  "1:200"
  )
  (navscale impstr impsc metsc)
)
(defun c:1-500 (/ impstr impsc metsc) 
  (setq impstr "1/32\" = 1'-0\""
        impsc  "1:384"
        metsc  "1:500"
  )
  (navscale impstr impsc metsc)
)
(defun c:1-750 (/ impstr impsc metsc) 
  (setq impstr "1/64\" = 1'-0\""
        impsc  "1:768"
        metsc  "1:750"
  )
  (navscale impstr impsc metsc)
)
(defun c:1-1000 (/ impstr impsc metsc) 
  (setq impstr "1\" = 80'"
        impsc  "1:960"
        metsc  "1:1000"
  )
  (navscale impstr impsc metsc)
)
(defun c:1-1250 (/ impstr impsc metsc) 
  (setq impstr "1\" = 100'"
        impsc  "1:1200"
        metsc  "1:1250"
  )
  (navscale impstr impsc metsc)
)
(defun c:1-2000 (/ impstr impsc metsc) 
  (setq impstr "1\" = 160'"
        impsc  "1:1920"
        metsc  "1:2000"
  )
  (navscale impstr impsc metsc)
)
(defun c:1-2500 (/ impstr impsc metsc) 
  (setq impstr "1\" = 200'"
        impsc  "1:2400"
        metsc  "1:2500"
  )
  (navscale impstr impsc metsc)
)
(defun c:1-5000 (/ impstr impsc metsc) 
  (setq impstr "1\" = 400'"
        impsc  "1:4800"
        metsc  "1:5000"
  )
  (navscale impstr impsc metsc)
)
