(defun navscale (impstr impsc metsc /) 
  (setvar "annoautoscale" -4)
  (if (= 1 (getvar "measurement")) 
    (progn 
      (setvar "cannoscale" metsc)
      (princ (strcat "Drawing scale set to " metsc))
      (princ)
    )
    (progn 
      (if (= "*1'*" (getvar "cannoscale")) 
        (setvar "cannoscale" impstr)
        (setvar "cannoscale" impsc)
      )
      (princ (strcat "Drawing scale set to " impstr))
      (princ)
    )
  )
  (command "regen")
  (princ)
)
