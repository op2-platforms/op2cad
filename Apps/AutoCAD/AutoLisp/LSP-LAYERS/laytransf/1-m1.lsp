; file usage: minor 1 commands and string data for laytranf function
;
;#region ACCESS
(defun c:m1-accs-clng (/ alpha omega) 
  (setq alpha "ACCS"
        omega "CLNG"
  )
  (search-m1 alpha omega)
)
(defun c:m1-accs-code (/ alpha omega) 
  (setq alpha "ACCS"
        omega "CODE"
  )
  (search-m1 alpha omega)
)
(defun c:m1-accs-domw (/ alpha omega) 
  (setq alpha "ACCS"
        omega "DOMW"
  )
  (search-m1 alpha omega)
)
(defun c:m1-accs-elec (/ alpha omega) 
  (setq alpha "ACCS"
        omega "ELEC"
  )
  (search-m1 alpha omega)
)
(defun c:m1-accs-evac (/ alpha omega) 
  (setq alpha "ACCS"
        omega "EVAC"
  )
  (search-m1 alpha omega)
)
(defun c:m1-accs-fire (/ alpha omega) 
  (setq alpha "ACCS"
        omega "FIRE"
  )
  (search-m1 alpha omega)
)
(defun c:m1-accs-flor (/ alpha omega) 
  (setq alpha "ACCS"
        omega "FLOR"
  )
  (search-m1 alpha omega)
)
(defun c:m1-accs-fndn (/ alpha omega) 
  (setq alpha "ACCS"
        omega "FNDN"
  )
  (search-m1 alpha omega)
)
(defun c:m1-accs-furn (/ alpha omega) 
  (setq alpha "ACCS"
        omega "FURN"
  )
  (search-m1 alpha omega)
)
(defun c:m1-accs-HVAC (/ alpha omega) 
  (setq alpha "ACCS"
        omega "HVAC"
  )
  (search-m1 alpha omega)
)
(defun c:m1-accs-code (/ alpha omega) 
  (setq alpha "ACCS"
        omega "ROOF"
  )
  (search-m1 alpha omega)
)
(defun c:m1-accs-site (/ alpha omega) 
  (setq alpha "ACCS"
        omega "SITE"
  )
  (search-m1 alpha omega)
)
(defun c:m1-accs-sswr (/ alpha omega) 
  (setq alpha "ACCS"
        omega "SSWR"
  )
  (search-m1 alpha omega)
)
(defun c:m1-accs-strc (/ alpha omega) 
  (setq alpha "ACCS"
        omega "STRC"
  )
  (search-m1 alpha omega)
)
(defun c:m1-accs-0001 (/ alpha omega) 
  (setq alpha "ACCS"
        omega "0001"
  )
  (search-m1 alpha omega)
)
(defun c:m1-accs-0002 (/ alpha omega) 
  (setq alpha "ACCS"
        omega "0002"
  )
  (search-m1 alpha omega)
)
(defun c:m1-accs-0003 (/ alpha omega) 
  (setq alpha "ACCS"
        omega "0003"
  )
  (search-m1 alpha omega)
)
;#endregion

;#region CEILING
(defun c:m1-clng-accs (/ alpha omega) 
  (setq alpha "CLNG"
        omega "ACCS"
  )
  (search-m1 alpha omega)
)
(defun c:m1-clng-code (/ alpha omega) 
  (setq alpha "CLNG"
        omega "CODE"
  )
  (search-m1 alpha omega)
)
(defun c:m1-clng-domw (/ alpha omega) 
  (setq alpha "CLNG"
        omega "DOMW"
  )
  (search-m1 alpha omega)
)
(defun c:m1-clng-elec (/ alpha omega) 
  (setq alpha "CLNG"
        omega "ELEC"
  )
  (search-m1 alpha omega)
)
(defun c:m1-clng-evac (/ alpha omega) 
  (setq alpha "CLNG"
        omega "EVAC"
  )
  (search-m1 alpha omega)
)
(defun c:m1-clng-fire (/ alpha omega) 
  (setq alpha "CLNG"
        omega "FIRE"
  )
  (search-m1 alpha omega)
)
(defun c:m1-clng-flor (/ alpha omega) 
  (setq alpha "CLNG"
        omega "FLOR"
  )
  (search-m1 alpha omega)
)
(defun c:m1-clng-fndn (/ alpha omega) 
  (setq alpha "CLNG"
        omega "FNDN"
  )
  (search-m1 alpha omega)
)
(defun c:m1-clng-furn (/ alpha omega) 
  (setq alpha "CLNG"
        omega "FURN"
  )
  (search-m1 alpha omega)
)
(defun c:m1-clng-HVAC (/ alpha omega) 
  (setq alpha "CLNG"
        omega "HVAC"
  )
  (search-m1 alpha omega)
)
(defun c:m1-clng-code (/ alpha omega) 
  (setq alpha "CLNG"
        omega "ROOF"
  )
  (search-m1 alpha omega)
)
(defun c:m1-clng-site (/ alpha omega) 
  (setq alpha "CLNG"
        omega "SITE"
  )
  (search-m1 alpha omega)
)
(defun c:m1-clng-sswr (/ alpha omega) 
  (setq alpha "CLNG"
        omega "SSWR"
  )
  (search-m1 alpha omega)
)
(defun c:m1-clng-strc (/ alpha omega) 
  (setq alpha "CLNG"
        omega "STRC"
  )
  (search-m1 alpha omega)
)
(defun c:m1-clng-0001 (/ alpha omega) 
  (setq alpha "CLNG"
        omega "0001"
  )
  (search-m1 alpha omega)
)
(defun c:m1-clng-0002 (/ alpha omega) 
  (setq alpha "CLNG"
        omega "0002"
  )
  (search-m1 alpha omega)
)
(defun c:m1-clng-0003 (/ alpha omega) 
  (setq alpha "CLNG"
        omega "0003"
  )
  (search-m1 alpha omega)
)
;#endregion

;#region FINE
(defun c:m1-fine-xfin (/ alpha omega) 
  (setq alpha "FINE"
        omega "XFIN"
  )
  (search-m1 alpha omega)
)
(defun c:m1-fine-thin (/ alpha omega) 
  (setq alpha "FINE"
        omega "THIN"
  )
  (search-m1 alpha omega)
)
(defun c:m1-fine-medm (/ alpha omega) 
  (setq alpha "FINE"
        omega "MEDM"
  )
  (search-m1 alpha omega)
)
(defun c:m1-fine-wide (/ alpha omega) 
  (setq alpha "FINE"
        omega "WIDE"
  )
  (search-m1 alpha omega)
)
(defun c:m1-fine-x~~~ (/ alpha omega) 
  (setq alpha "FINE"
        omega "X~~~"
  )
  (search-m1 alpha omega)
)
(defun c:m1-fine-x~~~ (/ alpha omega) 
  (setq alpha "FINE"
        omega "XX~~"
  )
  (search-m1 alpha omega)
)
(defun c:m1-fine-x~~~ (/ alpha omega) 
  (setq alpha "FINE"
        omega "XXX~"
  )
  (search-m1 alpha omega)
)
(defun c:m1-fine-x~~~ (/ alpha omega) 
  (setq alpha "FINE"
        omega "XXXX"
  )
  (search-m1 alpha omega)
)
(defun c:m1-fine-patt (/ alpha omega) 
  (setq alpha "FINE"
        omega "PATT"
  )
  (search-m1 alpha omega)
)
(defun c:m1-fine-scrn (/ alpha omega) 
  (setq alpha "FINE"
        omega "SCRN"
  )
  (search-m1 alpha omega)
)
;#endregion

;#region thin
(defun c:m1-thin-xfin (/ alpha omega) 
  (setq alpha "THIN"
        omega "XFIN"
  )
  (search-m1 alpha omega)
)
(defun c:m1-thin-fine (/ alpha omega) 
  (setq alpha "THIN"
        omega "FINE"
  )
  (search-m1 alpha omega)
)
(defun c:m1-thin-medm (/ alpha omega) 
  (setq alpha "THIN"
        omega "MEDM"
  )
  (search-m1 alpha omega)
)
(defun c:m1-thin-wide (/ alpha omega) 
  (setq alpha "THIN"
        omega "WIDE"
  )
  (search-m1 alpha omega)
)
(defun c:m1-thin-x~~~ (/ alpha omega) 
  (setq alpha "THIN"
        omega "X~~~"
  )
  (search-m1 alpha omega)
)
(defun c:m1-thin-x~~~ (/ alpha omega) 
  (setq alpha "THIN"
        omega "XX~~"
  )
  (search-m1 alpha omega)
)
(defun c:m1-thin-x~~~ (/ alpha omega) 
  (setq alpha "THIN"
        omega "XXX~"
  )
  (search-m1 alpha omega)
)
(defun c:m1-thin-x~~~ (/ alpha omega) 
  (setq alpha "THIN"
        omega "xxxx"
  )
  (search-m1 alpha omega)
)
(defun c:m1-thin-patt (/ alpha omega) 
  (setq alpha "THIN"
        omega "PATT"
  )
  (search-m1 alpha omega)
)
(defun c:m1-thin-scrn (/ alpha omega) 
  (setq alpha "THIN"
        omega "SCRN"
  )
  (search-m1 alpha omega)
)
;#endregion

;#region medm
(defun c:m1-medm-xfin (/ alpha omega) 
  (setq alpha "MEDM"
        omega "XFIN"
  )
  (search-m1 alpha omega)
)
(defun c:m1-medm-fine (/ alpha omega) 
  (setq alpha "MEDM"
        omega "FINE"
  )
  (search-m1 alpha omega)
)
(defun c:m1-medm-thin (/ alpha omega) 
  (setq alpha "MEDM"
        omega "THIN"
  )
  (search-m1 alpha omega)
)
(defun c:m1-medm-wide (/ alpha omega) 
  (setq alpha "MEDM"
        omega "WIDE"
  )
  (search-m1 alpha omega)
)
(defun c:m1-medm-x~~~ (/ alpha omega) 
  (setq alpha "MEDM"
        omega "X~~~"
  )
  (search-m1 alpha omega)
)
(defun c:m1-medm-x~~~ (/ alpha omega) 
  (setq alpha "MEDM"
        omega "XX~~"
  )
  (search-m1 alpha omega)
)
(defun c:m1-medm-x~~~ (/ alpha omega) 
  (setq alpha "MEDM"
        omega "XXX~"
  )
  (search-m1 alpha omega)
)
(defun c:m1-medm-x~~~ (/ alpha omega) 
  (setq alpha "MEDM"
        omega "xxxx"
  )
  (search-m1 alpha omega)
)
;#endregion

;#region wide
(defun c:m1-wide-xfin (/ alpha omega) 
  (setq alpha "WIDE"
        omega "XFIN"
  )
  (search-m1 alpha omega)
)
(defun c:m1-wide-fine (/ alpha omega) 
  (setq alpha "WIDE"
        omega "FINE"
  )
  (search-m1 alpha omega)
)
(defun c:m1-wide-thin (/ alpha omega) 
  (setq alpha "WIDE"
        omega "THIN"
  )
  (search-m1 alpha omega)
)
(defun c:m1-wide-medm (/ alpha omega) 
  (setq alpha "WIDE"
        omega "MEDM"
  )
  (search-m1 alpha omega)
)
(defun c:m1-wide-x~~~ (/ alpha omega) 
  (setq alpha "WIDE"
        omega "X~~~"
  )
  (search-m1 alpha omega)
)
(defun c:m1-wide-x~~~ (/ alpha omega) 
  (setq alpha "WIDE"
        omega "XX~~"
  )
  (search-m1 alpha omega)
)
(defun c:m1-wide-x~~~ (/ alpha omega) 
  (setq alpha "WIDE"
        omega "XXX~"
  )
  (search-m1 alpha omega)
)
(defun c:m1-wide-x~~~ (/ alpha omega) 
  (setq alpha "WIDE"
        omega "xxxx"
  )
  (search-m1 alpha omega)
)
;#endregion
